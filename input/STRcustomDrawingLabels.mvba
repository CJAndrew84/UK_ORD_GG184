Attribute VB_Name = "Main"
Option Explicit
'*--------------------------------------------------------------------------------------+
'
'   $Source: vba/customdrawings/Main.bas $
'
'   $Copyright: (c) 2016 Bentley Systems, Incorporated. All rights reserved. $
'
'   This program is confidential, proprietary and unpublished property of Bentley Systems
'   Inc. It may NOT be copied in part or in whole on any medium, either electronic or
'   printed, without the express written consent of Bentley Systems, Inc.
'
'--------------------------------------------------------------------------------------*/
Declare PtrSafe Sub mdlString_fromUors Lib "stdmdlbltin.dll" (ByVal uorString As String, ByVal uors As Double)

'--------------------------------------------------------------------------------------
'   This module contains example functions for customized formatting of variables
'   in custom labels on Structural drawings.
'
'   The names of the VBA project, the module (optional), and the Public function are
'   specified in the drawing resymbolization rule. When a member is processing during
'   drawing extraction that has the rule assigned to it, the VBA function is called.
'   The function is expected to look something like this:
'
'   Public Function customFormatter (handle As Long, value As String) As String
'       ...
'       customFormatter = ...
'   End Function
'
'   The first argument, "handle", can be used to get the STFLinearMemberList that
'   is currently being processed by drawing extraction (if you need it). Here's
'   how that's done:
'
'       Dim memberList As New STFLinearMemberList
'       Dim member As STFLinearMember
'       memberList.initReadOnlyFromHandle handle
'       Set member = memberList
'
'   The initReadOnlyFromHandle method is hidden as it's _only_ use is in VBA
'   functions for custom formatting of variables in custom labels on Structural
'   drawings. Also, do not edit the member; the changes will have no impact on
'   the drawing extraction.
'
'   The second argument, "value", is the variable's value as a String without any
'   special formatting.
'
'   The VBA function is expected to return the properly formatted string.
'--------------------------------------------------------------------------------------

'--------------------------------------------------------------------------------------
'   Truncate the section name at the last 'x' or 'X' character
'
'   This duplicates what happens when the "Abbreviate section name" toggle is checked
'   for the standard section name label.
'--------------------------------------------------------------------------------------
Public Function STRAbbreviateSectionName(handle As LongLong, value As String) As String
    Dim memberList As New STFLinearMemberList
    Dim sectName As String
    Dim charPos As Integer

    ' Initialize the member from the "handle" argument
    ' This step is required in order to reference any member attributes
    memberList.InitReadOnlyFromHandle handle

    ' Get the section name from the member
    sectName = memberList.AsSTFLinearMember.GetSectionName

    ' Truncate the name at the last 'x' (or 'X')
    charPos = InStrRev(sectName, "x", -1, vbTextCompare)
    If charPos <> 0 Then
        STRAbbreviateSectionName = VBA.Left$(sectName, charPos - 1)
    Else
        STRAbbreviateSectionName = sectName
    End If
End Function

'--------------------------------------------------------------------------------------
'   Truncate the member value at the last 'x' or 'X' character
'
'   This function truncates the attribute value that is passed to the function. It can
'   be used to abbreviate section names and other attributes, e.g. one of the user
'   strings.
'--------------------------------------------------------------------------------------
Public Function STRAbbreviateName(handle As Long, value As String) As String
    Dim charPos As Long

    ' Truncate the value at the last 'x' (or 'X')
    charPos = InStrRev(value, "x", -1, vbTextCompare)
    If charPos <> 0 Then
        STRAbbreviateName = VBA.Left$(value, charPos - 1)
    Else
        STRAbbreviateName = value
    End If
End Function

'--------------------------------------------------------------------------------------
'--------------------------------------------------------------------------------------
Private Sub AddSpacesAroundAllFractions(theString As String)
    If 0 <> InStr(theString, "/") Then
        theString = Replace(theString, "1/2", " 1/2 ")

        If 0 <> InStr(theString, "/4") Then
            theString = Replace(theString, "1/4", " 1/4 ")
            theString = Replace(theString, "3/4", " 3/4 ")
        End If

        If 0 <> InStr(theString, "/8") Then
            theString = Replace(theString, "1/8", " 1/8 ")
            theString = Replace(theString, "3/8", " 3/8 ")
            theString = Replace(theString, "5/8", " 5/8 ")
            theString = Replace(theString, "7/8", " 7/8 ")
        End If

    ' NEEDSWORK--Replace doesn't update the string correctly for 16th, 32nds, and 64ths
    '            as the smaller fraction strings can be substrings of the larger
    '            fraction strings. For example, replacing "1/16" with " 1/16 " will
    '            pick up "11/16" and do this to it--"1 1/16 "--the wrong result.
    End If
End Sub

'--------------------------------------------------------------------------------------
'   Reformat the section name so that the label will be output with stacked fractions.
'
'   Note: In order for stacked fractions to actually appear in the drawing, stacked
'         fractions must be enabled in the text style that will be used to display the
'         label and the MicroStation font specified by the text style must include
'         fractions.
'--------------------------------------------------------------------------------------
Public Function STRSectionNameWithStackedFractions(handle As LongLong, value As String) As String
    Dim memberList As New STFLinearMemberList
    Dim sectName As String

    ' Initialize the member from the "handle" argument
    ' This step is required in order to reference any member attributes
    memberList.InitReadOnlyFromHandle handle

    ' Get the section name from the member
    sectName = memberList.AsSTFLinearMember.GetSectionName

    ' Separate the fraction(s) from the rest of the string by spaces
    AddSpacesAroundAllFractions sectName
    STRSectionNameWithStackedFractions = sectName
End Function

'--------------------------------------------------------------------------------------
'   Reformat the name so that the label will be output with stacked fractions.
'
'   This function reformats the attribute value that is passed to the function. It can
'   be used to reformat section names and other attributes, e.g. one of the user
'   strings.

'   Note: In order for stacked fractions to actually appear in the drawing, stacked
'         fractions must be enabled in the text style that will be used to display the
'         label and the MicroStation font specified by the text style must include
'         fractions.
'--------------------------------------------------------------------------------------
Public Function STRNameWithStackedFractions(handle As Long, value As String) As String
    ' Separate the fraction(s) from the rest of the string by spaces
    AddSpacesAroundAllFractions value
    STRNameWithStackedFractions = value
End Function
'--------------------------------------------------------------------------------------
'   Replace ANY upper case X with a lower case 'x'
'
'--------------------------------------------------------------------------------------
Public Function STRLowerXSectionName(handle As LongLong, value As String) As String
    Dim memberList As New STFLinearMemberList
    Dim sectName As String
    Dim charPos As Integer

    ' Initialize the member from the "handle" argument
    ' This step is required in order to reference any member attributes
    memberList.InitReadOnlyFromHandle handle

    ' Get the section name from the member
    sectName = memberList.AsSTFLinearMember.GetSectionName

    ' Truncate the name at the last 'x' (or 'X')
    charPos = InStrRev(sectName, "x", -1, vbTextCompare)
    If charPos <> 0 Then
        sectName = Replace(sectName, "X", "x", 1, -1)
        STRLowerXSectionName = sectName
'        STRAbbreviateSectionName = Left$(sectName, charPos - 1)
    Else
        STRLowerXSectionName = sectName
    End If
End Function

'--------------------------------------------------------------------------------------
'
'   This function creates and returns a string which formats non-null attributes.
'   Specifically, if a STR member has:
'       1. section name             W18x35
'       2. shear studs (in User2)   45
'       3. camber (in User1)        3/4
'
'   A string will be created which looks like this:  W18X35 [45] <c=3/4">
'   If either 2. or 3. is null, the string will NOT contain [] or <>
'
'   NOTE: Not all fonts support the < > symbols.  To make the < > symbols appear correctly,
'   ensure the font you are using will actually place the < and >.
'
'--------------------------------------------------------------------------------------
Public Function STRCommonString(handle As LongLong, value As String) As String
    Dim memberList As New STFLinearMemberList
    Dim sectName As String
    Dim sCamber As String
    Dim sStuds As String
    Dim charPos As Integer
    Dim slen As Integer

    ' Initialize the member from the "handle" argument
    ' This step is required in order to reference any member attributes
    memberList.InitReadOnlyFromHandle handle

    ' Get the section name from the member
    STRCommonString = memberList.AsSTFLinearMember.GetSectionName

    ' Get the camber value from User1 string
    sCamber = memberList.AsSTFLinearMember.GetUserString(1)

    ' Get the User2 string = shear studs
    sStuds = memberList.AsSTFLinearMember.GetUserString(2)

    slen = Len(sStuds)
    If slen > 0 Then
        STRCommonString = STRCommonString & " [" & sStuds & "]"
    End If

    slen = Len(sCamber)
    If slen > 0 Then
        STRCommonString = STRCommonString & " <c=" & sCamber & ">"
    End If

End Function

Public Function STRTaperedSectionNames(handle As LongLong, value As String) As String
    Dim STF_SECTNAME_SEPARATOR As String
    Dim memberList As New STFLinearMemberList
    Dim sectName1 As String
    Dim sectName2 As String
    Dim charstr As String

    ' Initialize the member from the "handle" argument
    ' This step is required in order to reference any member attributes
    memberList.InitReadOnlyFromHandle handle

    ' Get the section names from the member.'sectName1' gets the name of the
    ' End 1 Section and 'sectName2' gets the name of the End 2 Section of the tapered member.
    sectName1 = memberList.AsSTFLinearMember.GetSectionName
    sectName2 = memberList.AsSTFLinearMember.GetSectionName2

    ' This step checks the 'STF_SECTNAME_SEPARATOR' configuration variable for
    ' the character to be used to separate the names.
    If ActiveWorkspace.IsConfigurationVariableDefined("STF_SECTNAME_SEPARATOR") = True Then
        charstr = ActiveWorkspace.ConfigurationVariableValue("STF_SECTNAME_SEPARATOR")
    Else
        charstr = " "
    End If

    'This step defines the value of the function after checking for the End 2 Section.
    If sectName2 = "" Then

        STRTaperedSectionNames = sectName1

    Else

        STRTaperedSectionNames = sectName1 & charstr & sectName2

    End If

End Function

Public Function STRAbbrTaperedSectionNames(handle As LongLong, value As String) As String
    Dim STF_SECTNAME_SEPARATOR As String
    Dim memberList As New STFLinearMemberList
    Dim sectName1 As String
    Dim sectName2 As String
    Dim charstr As String
    Dim charPos1 As Integer
    Dim charPos2 As Integer

    ' Initialize the member from the "handle" argument
    ' This step is required in order to reference any member attributes
    memberList.InitReadOnlyFromHandle handle

    ' Get the section names from the member.'sectName1' is the name of the End 1 Section
    ' and 'sectName2' is the name of the End 2 Section of the Tapered Beam.
    sectName1 = memberList.AsSTFLinearMember.GetSectionName
    sectName2 = memberList.AsSTFLinearMember.GetSectionName2

    ' Truncate the names at the last 'x' (or 'X')
    charPos1 = InStrRev(sectName1, "x", -1, vbTextCompare)
    charPos2 = InStrRev(sectName2, "x", -1, vbTextCompare)

    ' This step checks the 'STF_SECTNAME_SEPARATOR' configuration variable for
    ' the character to be used to separate the names.
    If ActiveWorkspace.IsConfigurationVariableDefined("STF_SECTNAME_SEPARATOR") = True Then
        charstr = ActiveWorkspace.ConfigurationVariableValue("STF_SECTNAME_SEPARATOR")
    Else
        charstr = " "
    End If

    'This step defines the value of the function after checking for the End 2 Section.
    If sectName2 = "" Then

        If charPos1 <> 0 Then
            STRAbbrTaperedSectionNames = VBA.Left$(sectName1, charPos1 - 1)
        Else
            STRAbbrTaperedSectionNames = sectName1
        End If

    Else

        If charPos1 <> 0 And charPos2 <> 0 Then
            STRAbbrTaperedSectionNames = VBA.Left$(sectName1, charPos1 - 1) & charstr & VBA.Left$(sectName2, charPos2 - 1)
        Else
            STRAbbrTaperedSectionNames = sectName1 & charstr & sectName2
        End If

    End If

End Function

'*----------------------------------------------------------------------------------*//**
' @description
'
' @bsimethod                                                    Bentley.Systems 02/2007
'---------------+---------------+---------------+---------------+---------------+------*/
Public Function SectionWithStudCount(handle As LongLong, value As String) As String

    Dim memberList          As New STFLinearMemberList
    Dim sectNameLabel       As String
    Dim studCountLabel      As String

    studCountLabel = ""

    ' Initialize the member from the "handle" argument
    ' This step is required in order to reference any member attributes
    memberList.InitReadOnlyFromHandle handle

    ' Get the section name from the member
    sectNameLabel = memberList.AsSTFLinearMember.GetSectionName

    ' process only values that are not empty
    If (Not Len(value) = 0) Then

        Dim STUDS_STRING_BEGIN  As String
        Dim STUDS_STRING_END    As String

        STUDS_STRING_BEGIN = "["            ' This string will be used before the number of studs
        STUDS_STRING_END = "]"              ' This string will be used after the number of studs

        ' build final camber with special start/end charaters
        studCountLabel = sectNameLabel + " " + STUDS_STRING_BEGIN + value + STUDS_STRING_END

    Else

        ' no studs on this member so just return the section label
        studCountLabel = sectNameLabel

    End If

    SectionWithStudCount = studCountLabel

End Function

'*----------------------------------------------------------------------------------*//**
' @description  "helper" function to determin if integer is even.  Return True if value
'               is even otherwise False.
' @bsimethod                                                    Bentley.Systems 02/2007
'---------------+---------------+---------------+---------------+---------------+------*/
Private Function IsEven(value As Long) As Boolean

    Dim status  As Boolean

    status = False

    If value Mod 2 = 0 Then
        status = True
    End If

    IsEven = status

End Function

'*----------------------------------------------------------------------------------*//**
' @description  Alternative stud count customization that makes all stud count
'               values even.
' @bsimethod                                                    Bentley.Systems 02/2007
'---------------+---------------+---------------+---------------+---------------+------*/
Public Function SectionWithEvenStudCount(handle As LongLong, value As String) As String

    Dim memberList          As New STFLinearMemberList
    Dim sectNameLabel       As String
    Dim studCountLabel      As String

    studCountLabel = ""

    ' Initialize the member from the "handle" argument
    ' This step is required in order to reference any member attributes
    memberList.InitReadOnlyFromHandle handle

    ' Get the section name from the member
    sectNameLabel = memberList.AsSTFLinearMember.GetSectionName

    ' process only values that are not empty
    If (Not Len(value) = 0) Then

        Dim splitString()       As String
        Dim STUDS_STRING_BEGIN  As String
        Dim STUDS_STRING_END    As String
        Dim position            As Integer
        Dim i                   As Integer
        Dim tempStudCount       As Long

        STUDS_STRING_BEGIN = "["            ' This string will be used before the number of studs
        STUDS_STRING_END = "]"              ' This string will be used after the number of studs

        position = 0

        ' split value for cases where there are groups of studs
        splitString = Split(value, " ")

        ' process tokenized members and build stud count which contains even values
        For i = 0 To UBound(splitString)

            tempStudCount = CInt(splitString(i))

            ' determine if stud count is even and adjust up
            If (Not True = IsEven(tempStudCount)) Then
                tempStudCount = tempStudCount + 1
            End If

            ' check if label has a value in it; if so then put space between values
            If (Not Len(studCountLabel) = 0) Then
                studCountLabel = studCountLabel + " " + CStr(tempStudCount)
            Else
                studCountLabel = CStr(tempStudCount)
            End If

        Next

        ' build final camber with special start/end charaters
        studCountLabel = sectNameLabel + " " + STUDS_STRING_BEGIN + studCountLabel + STUDS_STRING_END

    Else

        ' no studs on this member so just return the section label
        studCountLabel = sectNameLabel

    End If

    SectionWithEvenStudCount = studCountLabel

End Function
'*----------------------------------------------------------------------------------*//**
' @description Create label for End Shear + unit label ("6k"), shear values smaller than
'              a minimum value will be set to the minimum value (min value determined by
'              force unit setting in the file)
'
' @bsimethod                                                    Bentley.Systems 11/2008
'---------------+---------------+---------------+---------------+---------------+------*/
'   This function has two input arguments and returns a string. The two input arguments are:
'      1) handle As Long,   <- This argument makes it possible for this function to reference any member attribute
'      2) shearValue As String   <- This argument is the value (string) of the endshear.
'
'   Specifically, if a STR member has a datagroup attribute of:
'            SteelBeamResults/SteelBeamResults/Shear/@end1shear, and/or
'            SteelBeamResults/SteelBeamResults/Shear/@end2shear
'       and a Structural drawing rule passes an endshear to this function as argument 2 (value),
'   Then:
'       A string will be created which looks like this:  "6k", or "26kN", or "6000lb", etc.
'
'   If this function is called from a drawing rule, and the shear attribute is less than a minimum value (as
'   determined by the Force units in the design file), then the minimum value will be returned in the label. If
'   the shear value is larger than the minimum value, the actual value will be used in the label.
'   This function is intended to be called twice for each structural member (once for each end)
'
Public Function EndShear(handle As LongLong, shearValue As String) As String

    ' Call shear label format function, third argument tells to use Minimum shear value setting
    EndShear = EndShearFormatLabel(handle, shearValue, False)

End Function

'*----------------------------------------------------------------------------------*//**
' @description Create label for End Shear + unit label ("6k"), but do not display any zero shear values
'
' @bsimethod                                                    Bentley.Systems 11/2008
'---------------+---------------+---------------+---------------+---------------+------*/
'   This function is similar to EndShearMinimumValues, except for two differences:
'       1) if this function is called from a drawing rule, and the shear attribute is zero,
'          no label will be created or returned.
'       2) no minimum shear value settings are used.
'
Public Function EndShearNoZeros(handle As LongLong, shearValue As String) As String

    ' Call shear label format function, third argument tells to not display zero shear values
    EndShearNoZeros = EndShearFormatLabel(handle, shearValue, True)

End Function

'*----------------------------------------------------------------------------------*//**
' @description Create and format string label for End Shear values
'
' @bsimethod                                                    Bentley.Systems 11/2008
'---------------+---------------+---------------+---------------+---------------+------*/
'
'   This function has three input arguments and returns a string. The input arguments are:
'      1) handle As Long,  <- This argument makes it possible for this function to reference any member attribute
'      2) shearValue As String, <- This argument is the value (string) of the endshear.
'      3) suppressZeros As Boolean  <- This argument determines if zero value shears should be displayed or not

'   This function creates and returns a string which formats an End Shear value.
'
Public Function EndShearFormatLabel(handle As LongLong, shearValue As String, suppressZeros As Boolean) As String

    Dim MINIMUM_SHEAR_TO_DISPLAY As Double
    Dim reactionLabel As String
    Dim unitLabel     As String
    Dim memberList    As New STFLinearMemberList
    Dim forceUnit     As TFdLoadsForceUnit
    Dim shear         As Double

    reactionLabel = ""
    unitLabel = ""

    ' Initialize the member from the "handle" argument
    ' This step is required in order to reference any member attributes
    memberList.InitReadOnlyFromHandle handle

    ' convert string to double
    shear = CDbl(shearValue)

    ' get force unit
    forceUnit = memberList.AsSTFLinearMember.GetForceUnit

    ' create unit string based on force unit
    If forceUnit = STFdForceUnitKilograms Then
        unitLabel = "kg"
        MINIMUM_SHEAR_TO_DISPLAY = 2721.5   '6k min = 2721.5 kg
    ElseIf forceUnit = STFdForceUnitKiloNewtons Then
        unitLabel = "kN"
        MINIMUM_SHEAR_TO_DISPLAY = 26.7     '6k min = 26.7 kN
    ElseIf forceUnit = STFdForceUnitNewtons Then
        unitLabel = "N"
        MINIMUM_SHEAR_TO_DISPLAY = 10#      '6k min = 267,000 N
    ElseIf forceUnit = STFdForceUnitKips Then
        unitLabel = "k"
        MINIMUM_SHEAR_TO_DISPLAY = 6#       '6k min
    ElseIf forceUnit = STFdForceUnitPoundsForce Then
        unitLabel = "lb"
        MINIMUM_SHEAR_TO_DISPLAY = 6000#    '6k min = 6,000 lbs
    ElseIf forceUnit = STFdForceUnitTonsForce Then
        unitLabel = "ton"
        MINIMUM_SHEAR_TO_DISPLAY = 3#       '6k min = 3 tons
    Else
        unitLabel = "unknown"
        MINIMUM_SHEAR_TO_DISPLAY = 6#       '6k min
    End If

    If suppressZeros = True Then
       If (shear = 0) Then
            EndShearFormatLabel = ""
            Exit Function
        End If
    ElseIf (Abs(shear) < MINIMUM_SHEAR_TO_DISPLAY) Then
            shear = MINIMUM_SHEAR_TO_DISPLAY
    End If

    ' Round the shear value up to the nearest whole number,
    ' change the second argument (from 0) to display decimal places, etc.
    If shear > 0 Then
        shear = Math.Round(shear + 0.5, 0)
    ElseIf shear < 0 Then
        shear = Math.Round(shear - 0.5, 0)
    End If


    ' convert shear back to a string and append unit string
    reactionLabel = CStr(shear) + unitLabel

    EndShearFormatLabel = reactionLabel

End Function


'*----------------------------------------------------------------------------------*//**
' @description  Alternative camber customization with format c=<value>; for
'               example c=3/4".
' @bsimethod                                                    Bentley.Systems 02/2007
'---------------+---------------+---------------+---------------+---------------+------*/
Public Function CamberWithLabel(handle As LongLong, value As String) As String

    Dim memberList          As New STFLinearMemberList
    Dim camberLabel         As String
    Dim camberUnit          As String
    Dim camber              As Double

    camberLabel = VBA.Space(1024)
    camberUnit = ""

    ' Initialize the member from the "handle" argument
    ' This step is required in order to reference any member attributes
    memberList.InitReadOnlyFromHandle handle
    memberList.AsSTFLinearMember.GetCamber camber

    If (camber <> 0) Then

        If VBA.UCase(ActiveModelReference.SubUnit.Label) = "MM" Then
            camberUnit = "mm"
        ElseIf VBA.UCase(ActiveModelReference.SubUnit.Label) = "IN" Or ActiveModelReference.SubUnit.Label = """" Then
            camberUnit = """"
        ElseIf VBA.UCase(ActiveModelReference.SubUnit.Label) = "FT" Or ActiveModelReference.SubUnit.Label = "'" Then
            camberUnit = "'"
        ElseIf VBA.UCase(ActiveModelReference.SubUnit.Label) = "M" Then
            camberUnit = "M"
        End If

        If ActiveModelReference.StorageUnit.System = msdMeasurementSystemEnglish Then

            camber = ActiveModelReference.UORsPerSubUnit * camber
            mdlString_fromUors camberLabel, camber
            camberLabel = VBA.Left$(camberLabel, InStr(1, camberLabel, vbNullChar) - 1)

            ' strip to sub unit
            camberLabel = VBA.Right$(camberLabel, Len(camberLabel) - InStr(1, camberLabel, ":"))
            ' strip leading zero and keep remaining fraction
            camberLabel = VBA.Right$(camberLabel, Len(camberLabel) - InStr(1, camberLabel, "0"))
            ' strip any leading or trailing spaces
            camberLabel = VBA.Trim(camberLabel)
        Else
            camber = Math.Round(camber, 0)
            camberLabel = CStr(camber)
        End If

        ' build final camber with special start/end charaters
        camberLabel = "c=" + camberLabel + camberUnit

    End If

    CamberWithLabel = camberLabel

End Function

'*----------------------------------------------------------------------------------*//**
' @description
'
' @bsimethod                                                    Bentley.Systems 02/2007
'---------------+---------------+---------------+---------------+---------------+------*/
Public Function CamberWithAngleBrackets(handle As LongLong, value As String) As String

    Dim memberList          As New STFLinearMemberList
    Dim camberLabel         As String
    Dim CAMBER_STRING_BEGIN As String
    Dim CAMBER_STRING_END   As String
    Dim camberUnit          As String
    Dim camber              As Double

    CAMBER_STRING_BEGIN = "<"    ' This string will be used before the value of the camber
    CAMBER_STRING_END = ">"       ' This string will be used after the camber value

    camberLabel = VBA.Space(1024)
    camberUnit = ""

    ' Initialize the member from the "handle" argument
    ' This step is required in order to reference any member attributes
    memberList.InitReadOnlyFromHandle handle
    memberList.AsSTFLinearMember.GetCamber camber

    If (camber <> 0) Then

        If VBA.UCase(ActiveModelReference.SubUnit.Label) = "MM" Then
            camberUnit = "mm"
        ElseIf VBA.UCase(ActiveModelReference.SubUnit.Label) = "IN" Or ActiveModelReference.SubUnit.Label = """" Then
            camberUnit = """"
        ElseIf VBA.UCase(ActiveModelReference.SubUnit.Label) = "FT" Or ActiveModelReference.SubUnit.Label = "'" Then
            camberUnit = "'"
        ElseIf VBA.UCase(ActiveModelReference.SubUnit.Label) = "M" Then
            camberUnit = "M"
        End If

        If ActiveModelReference.StorageUnit.System = msdMeasurementSystemEnglish Then

            camber = ActiveModelReference.UORsPerSubUnit * camber
            mdlString_fromUors camberLabel, camber
            camberLabel = VBA.Left$(camberLabel, InStr(1, camberLabel, vbNullChar) - 1)

            ' strip to sub unit
            camberLabel = VBA.Right$(camberLabel, Len(camberLabel) - InStr(1, camberLabel, ":"))
            ' strip leading zero and keep remaining fraction
            camberLabel = VBA.Right$(camberLabel, Len(camberLabel) - InStr(1, camberLabel, "0"))
            ' strip any leading or trailing spaces
            camberLabel = VBA.Trim(camberLabel)
        Else
            camber = Math.Round(camber, 0)
            camberLabel = CStr(camber)
        End If

        ' build final camber with special start/end charaters
        camberLabel = CAMBER_STRING_BEGIN + camberLabel + camberUnit + " " + CAMBER_STRING_END

    End If

    CamberWithAngleBrackets = camberLabel

End Function
