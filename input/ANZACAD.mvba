Attribute VB_Name = "Module1"
Private Sub XML_Load_Click()
    Dim myxML As New MSXML2.DOMDocument60
    Dim myXElem As MSXML2.IXMLDOMElement
    Dim myXRecord As MSXML2.IXMLDOMElement
    Dim myXField As MSXML2.IXMLDOMElement
    Dim ANZACAD As New MSXML2.DOMDocument60
    Dim ANZAElem As MSXML2.IXMLDOMElement
    Dim ANZARecord As MSXML2.IXMLDOMElement
    Dim ANZAField As MSXML2.IXMLDOMElement
    Dim path As String
    Const CurrentFolder As String = "$(_dgndir)"
    Dim xmlpath As String
    Dim ANZACADpath As String
    Dim ParentPath As String
    Dim path1 As String
    
    path = ActiveWorkspace.ExpandConfigurationVariable(CurrentFolder)
    path1 = Left$(path, Len(path) - 1)
    ParentPath = Left$(path1, InStrRev(path1, "\"))
    myxML.async = False
    myxML.validateOnParse = False
    xmlpath = path & "_Project Setting.xml"
    If myxML.Load(xmlpath) Then
        Debug.Print "Test1"
        
        Set myXElem = myxML.documentElement
        For Each myXRecord In myXElem.childNodes
            Debug.Print "***NEW RECORD***"
            
            'For Each myXField In myXRecord.childNodes
            '    Debug.Print myXField.baseName & ".." & myXField.Text
            'Next myXField
            
            Debug.Print myXRecord.tagName & "-" & myXRecord.Text
            ANZACADpath = myXRecord.Text
            
            If ANZACAD.Load(ParentPath & (Right$(ANZACADpath, Len(ANZACADpath) - 3))) Then
                Debug.Print "Test2"
                
                Set ANZAElem = ANZACAD.documentElement
                For Each ANZARecord In ANZAElem.childNodes
                    Debug.Print "***NEW RECORD***"
            
                    For Each ANZAField In ANZARecord.childNodes
                        Debug.Print ANZAField.baseName & ".." & ANZAField.Text
                    Next ANZAField
                    
                Next ANZARecord
                
            End If
            
        Next myXRecord
                
    End If
        
End Sub
