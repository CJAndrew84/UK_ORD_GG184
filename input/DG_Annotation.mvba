Attribute VB_Name = "Door"
'*----------------------------------------------------------------------+
'     DG_Annotation Door - Formats custom annotation for Bentley
'                           Architecture Doors
'     $Source: Space.DG_Annotation.mvba
'
' Copyright (c) 2009-11;  Bentley Systems, Inc., 685 Stockton Drive,
'                      Exton PA, 19341-0678, USA.  All Rights Reserved.
'
'----------------------------------------------------------------------*/

Public Sub DoorID_RoomNumber()
    Dim DoorID As String

    DoorID = KeyinArguments
    DoorRoomNumber = Left$(DoorID, Len(DoorID) - 1)
    KeyinArguments = DoorRoomNumber
End Sub

Public Sub DoorID_DoorLetter()
    Dim DoorID As String

    DoorID = KeyinArguments
    DoorIDLetter = Right$(DoorID, 1)
    KeyinArguments = DoorIDLetter
End Sub

Attribute VB_Name = "Space"
Global SpaceLabel1 As String
Global SpaceLabel2 As String
Global SpaceLabel3 As String
Global SpaceAbvLabel As String
Global SpaceArea As String

Declare PtrSafe Sub mdlString_fromUors Lib "stdmdlbltin.dll" (ByVal uor_string As String, ByVal uors As Double)
Declare PtrSafe Sub mdlString_fromUorsWithUnits Lib "stdmdlbltin.dll" (ByVal uor_string As String, ByVal uors As Double, ByVal units As Integer)
'*----------------------------------------------------------------------+
'     DG_Annotation Space - Formats custom annotation for Bentley
'                           Architecture Spaces in imperial units
'     $Source: Space.DG_Annotation.mvba
'       1.4:Added support for fractions in 1/8" increments on ceiling height
'       1.5:Update includes fix for improperly functioning FIX command in ceiling height
'
' Copyright (c) 2009-11;  Bentley Systems, Inc., 685 Stockton Drive,
'                      Exton PA, 19341-0678, USA.  All Rights Reserved.
'
'----------------------------------------------------------------------*/
Public Function SplitSpaceLabel(FullSpaceLabel As String) As String
    Dim iMaximumLengthOfLabel As Integer
    Dim iMarker As Integer
    Dim iWordCount As Integer
    Dim Words() As String

    'Change the iMaximumLengthOfLabel to change
    'the maximum length of each line of the label
    'This will be automatically overridden if the label is longer than 3 times iMaximumLengthOfLabel
    iMaximumLengthOfLabel = 16

    If Len(SpaceAbvLabel) > 1 Then
        'If this is true, an abbreviation or user split space name has been stored in Label2 in the datagroup data for that space.
        If InStr(SpaceAbvLabel, "~") > 0 Then
            'If this is true, the space label in label2 has ~ symbols to split the lines in the label
            'Split the label into lines and store in an array
            Words = Split(SpaceAbvLabel, "~")
            'Assign the lines to the SpaceLabel variables
            SpaceLabel3 = Words(UBound(Words))
            SpaceLabel2 = Words(UBound(Words) - 1)
            If UBound(Words) > 1 Then
                SpaceLabel1 = Words(0)
                SpaceAbvLabel = ""
            End If
        Else
            'If this is true, an abbreviation has been stored in Label2 in the datagroup data for that space.
            'Use this instead of the contents of Label in the datagroup data.
            SpaceLabel1 = " "
            SpaceLabel2 = " "
            SpaceLabel3 = SpaceAbvLabel
            SpaceAbvLabel = ""
        End If
    Else
    'Breakdown the Label field into appropriate lines of predetermined size
        'Remove extra spaces at begining and end of label
        If FullSpaceLabel <> " " Then FullSpaceLabel = Trim(FullSpaceLabel)
        'Determine the overall label length
        iLabelLength = Len(FullSpaceLabel)

        'If the label length exceeds 3 times the Maximum Length of label line, increase the maximum
        If iLabelLength > 3 * iMaximumLengthOfLabel Then iMaximumLengthOfLabel = Int(iLabelLength / 3)

        Select Case iLabelLength
            Case Is < iMaximumLengthOfLabel + 1
            'The label will fit on one line.
                SpaceLabel1 = " "
                SpaceLabel2 = " "
                SpaceLabel3 = FullSpaceLabel
            Case Else
                'Split the label into individual words and store in an array
                Words = Split(FullSpaceLabel, " ")
                'Step through array and build each line without exceeding the maximum label line length
                For iWordCount = UBound(Words) To 0 Step -1
                    Select Case iMarker + Len(Words(iWordCount))
                        Case Is < iMaximumLengthOfLabel + 1
                        'Add active word to Label3(the line closest to the space number)
                            If Len(SpaceLabel3) > 1 Then
                                SpaceLabel3 = Words(iWordCount) & " " & SpaceLabel3
                            Else
                                SpaceLabel3 = Words(iWordCount)
                            End If
                            iMarker = Len(SpaceLabel3)
                        Case Is < (2 * iMaximumLengthOfLabel) + 1
                        'Add active word to Label2 (the middle line)
                            If Len(SpaceLabel2) > 1 Then
                                SpaceLabel2 = Words(iWordCount) & " " & SpaceLabel2
                            Else
                                SpaceLabel2 = Words(iWordCount)
                            End If
                            iMarker = Len(SpaceLabel2) + Len(SpaceLabel3)
                        Case Else
                        'Add active word to Label1 (the top line)
                            If Len(SpaceLabel1) > 1 Then
                                SpaceLabel1 = Words(iWordCount) & " " & SpaceLabel1
                            Else
                                SpaceLabel1 = Words(iWordCount)
                            End If
                            iMarker = Len(SpaceLabel1) + Len(SpaceLabel2) + Len(SpaceLabel3)
                    End Select
                Next iWordCount
        End Select
    End If
End Function
Public Function CalculateVolume(CeilingHeight As String) As String
    Dim lFeet As Double

    Dim iColonLocation As Integer
    Dim iNumberOfDecimals As Integer

    'Change the value of iNumberOfDecimals to control
    'the number of decimals to show in the Volume calculation
    iNumberOfDecimals = 0

    'Ceiling Height is sent to the macro in UOR.  Convert that to Feet.
    lFeet = Val(CeilingHeight) / ActiveModelReference.UORsPerStorageUnit
    CalculateVolume = CStr(Round(lFeet * Val(SpaceArea), iNumberOfDecimals)) & " Cu" & ActiveModelReference.masterUnit.Label
End Function
'  Truncates a buffer to just contain the string that
'  the C function returned.
Function TruncateAtEOS(str As String) As String
    If str <> "" Then  ' This test avoids exception on zero-length string
        TruncateAtEOS = Left$(str, InStr(1, str, vbNullChar) - 1)
    End If
End Function

Public Function CeilingHeightFormat(CeilingHeight As String) As String

    Dim newString As String
    Dim UorValue As Double
    UorValue = Val(CeilingHeight)

    newString = String(64, 0)
    Call mdlString_fromUors(newString, UorValue)

    newString = TruncateAtEOS(newString)

    Dim paramvalues() As String
    paramvalues = Split(newString, ":")

    Dim masterUnit As String
    Dim subUnit As String
    Dim masterUnitLabel As String
    Dim subUnitLabel As String

    masterUnitLabel = ActiveModelReference.masterUnit.Label
    subUnitLabel = ActiveModelReference.subUnit.Label

    masterUnit = paramvalues(0)

    Dim masterString As String
    masterString = masterUnit & " " & masterUnitLabel

    If UBound(paramvalues) > 0 Then
        subUnit = paramvalues(1)
        CeilingHeightFormat = masterString & "-" & subUnit & subUnitLabel
    Else
        CeilingHeightFormat = masterString
    End If

'    CeilingHeightFormat = paramValues (0) & ActiveModelReference.MasterUnit.Label & "-"  & paramValues (1) & ActiveModelReference.SubUnit.Label
'    CeilingHeightFormat = newString



End Function
Function FractionInches(lFractionalInches As Double) As String
    Dim sFractionalInches As String
    sFractionalInches = Right$(CStr(lFractionalInches), 3)

    Select Case lFractionalInches
    Case Is = 0
        FractionInches = ActiveModelReference.subUnit.Label
    Case Is = 0.125
        FractionInches = " 1/8" & ActiveModelReference.subUnit.Label
    Case Is = 0.25
        FractionInches = " 1/4" & ActiveModelReference.subUnit.Label
    Case Is = 0.375
        FractionInches = " 3/8" & ActiveModelReference.subUnit.Label
    Case Is = 0.5
        FractionInches = " 1/2" & ActiveModelReference.subUnit.Label
    Case Is = 0.625
        FractionInches = " 5/8" & ActiveModelReference.subUnit.Label
    Case Is = 0.75
        FractionInches = " 3/4" & ActiveModelReference.subUnit.Label
    Case Is = 0.875
        FractionInches = " 7/8" & ActiveModelReference.subUnit.Label
    Case Else
        FractionInches = "." & sFractionalInches & ActiveModelReference.subUnit.Label
    End Select

End Function

Public Sub InitGlobals()
    SpaceLabel1 = " "
    SpaceLabel2 = " "
    SpaceLabel3 = " "
    SpaceAbvLabel = ""
End Sub

Public Sub Label1()
    Dim SpaceLabel As String
    SpaceLabel1 = " "
    SpaceLabel2 = " "
    SpaceLabel3 = " "

    SpaceLabel = SplitSpaceLabel(KeyinArguments)
    KeyinArguments = SpaceLabel1
    SpaceAbvLabel = " "
End Sub
Public Sub Label2()
    KeyinArguments = SpaceLabel2
End Sub
Public Sub Label3()
    KeyinArguments = SpaceLabel3
End Sub
Public Sub AbbreviatedLabel()
    Dim sBlankSpace As String

    sBlankSpace = " "
    SpaceAbvLabel = KeyinArguments
    KeyinArguments = sBlankSpace
End Sub
Public Sub Volume()
    Dim CeilingHeight As String
    CeilingHeight = KeyinArguments

    KeyinArguments = CalculateVolume(CeilingHeight)
End Sub
Public Sub MetricVolume()
    Volume
End Sub

Public Sub CeilingHeight()
    Dim CeilingHeight As String
    CeilingHeight = KeyinArguments

    KeyinArguments = CeilingHeightFormat(CeilingHeight)
End Sub
Public Sub MetricCeilingHeight()
    CeilingHeight
End Sub

Public Sub Area()
    Dim sSpaceArea As String
    Dim iNumberOfDecimals As Integer

    'Change the value of iNumberOfDecimals to control
    'the number of decimals to show in the Actual Area calculation
    iNumberOfDecimals = 0

    SpaceArea = KeyinArguments
    sSpaceArea = CStr(Round(Val(SpaceArea), iNumberOfDecimals)) & " Sq" & ActiveModelReference.masterUnit.Label
    KeyinArguments = sSpaceArea
End Sub
Public Sub MetricArea()
    Area
End Sub

Public Sub ProgramArea()
    Dim sSpaceArea As String
    Dim iNumberOfDecimals As Integer

    'Change the value of iNumberOfDecimals to control
    'the number of decimals to show in the Actual Area calculation
    iNumberOfDecimals = 0
    sSpaceArea = CStr(Round(Val(KeyinArguments), iNumberOfDecimals)) & " Sq" & ActiveModelReference.masterUnit.Label
    KeyinArguments = sSpaceArea
End Sub
Public Sub MetricProgramArea()
    ProgramArea
End Sub
