Attribute VB_Name = "PlaceSpaceCommand"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Implements IPrimitiveCommandEvents
Const Building = 1
Const Gross = 2
Const Dept = 3
Const Room = 4
Const Unknown = 10
Public xlApp As Excel.Application
Public xlWorkBook As Excel.Workbook
Public xlWorkSheet As Excel.Worksheet

Const MAX_SPACES = 100
Private m_SpaceNames(0 To MAX_SPACES) As String
Private m_SpaceArea(0 To MAX_SPACES) As Double
Private m_SpaceType(0 To MAX_SPACES) As Long
Private m_nSpaces As Integer
Private Sub IPrimitiveCommandEvents_Cleanup()

End Sub
Private Sub IPrimitiveCommandEvents_DataPoint(Point As Point3d, ByVal View As View)
    Dim lowerLeft As Point3d
    Dim upperRight As Point3d
    Dim i As Integer, size As Double
    
    lowerLeft = Point
    For i = LBound(m_SpaceNames) To m_nSpaces
        size = Sqr(m_SpaceArea(i))
        upperRight.X = lowerLeft.X + size
        upperRight.Y = lowerLeft.Y + size
        upperRight.Z = lowerLeft.Z
        
        CadInputQueue.SendKeyin "atfplace excel " & m_SpaceType(i) & " " & m_SpaceNames(i)
        CadInputQueue.SendDataPoint lowerLeft, View
        CadInputQueue.SendDataPoint upperRight, View
        
        lowerLeft.X = lowerLeft.X + size + (size / 4)
    Next i
    
End Sub

Private Sub IPrimitiveCommandEvents_Dynamics(Point As Point3d, ByVal View As View, ByVal DrawMode As MsdDrawingMode)
    Dim i As Integer
    Dim side As Double
    Dim oEl As ShapeElement
    Dim Vertices(5) As Point3d
    Dim startingPoint As Point3d
    
    startingPoint = Point
    
    For i = LBound(m_SpaceNames) To UBound(m_SpaceNames)
        side = Sqr(m_SpaceArea(i))
        Vertices(0) = startingPoint
        Vertices(1) = Vertices(0)
        Vertices(1).X = Vertices(1).X + side
        Vertices(2) = Vertices(1)
        Vertices(2).Y = Vertices(2).Y + side
        Vertices(3) = Vertices(0)
        Vertices(3).Y = Vertices(3).Y + side
        Vertices(4) = Vertices(0)
        
        Set oEl = CreateShapeElement1(Nothing, Vertices, msdFillModeNotFilled)
'        Set oEl = ShapeElement.Area = m_SpaceArea(i)
        oEl.Color = m_SpaceType(i)
        startingPoint.X = startingPoint.X + side + (side / 4)
        oEl.Redraw DrawMode
    Next i
End Sub

Private Sub IPrimitiveCommandEvents_Keyin(ByVal Keyin As String)

End Sub
Private Sub IPrimitiveCommandEvents_Reset()
    CommandState.StartPrimitive Me
    m_nSpaces = 0
End Sub
Private Sub IPrimitiveCommandEvents_start()
    ShowCommand "VBA PlaceSpace Example"
    ShowPrompt "Select Starting Point"
    m_nSpaces = LBound(m_SpaceNames) - 1
    getExcel
    CommandState.StartDynamics
End Sub

Sub getExcel()
    Dim selectedRange As Range
    Dim thisSheet As String
    Dim rngCell As Range
    Dim rowCell As Range
    Dim SpaceType As Integer, RowIndex As Integer
    Dim NameString As String
    Dim FillColumn As String
    Dim areaValue As Long
    Dim status
    
    Err.Clear ' Clear Err Object
    On Error GoTo ErrorHandle
    Set xlApp = GetObject(, "Excel.Application")
    
        Set xlWorkBook = xlApp.ActiveWorkbook
        Set xlWorkSheet = xlApp.ActiveSheet
    
        xlWorkBook.Activate
        xlWorkSheet.Activate
    
        thisSheet = xlWorkSheet.Name
    
        Set rngCell = xlApp.Selection
        Dim selectRows As Integer
        Dim selectColumns As Integer
    
        selectRows = rngCell.Rows.Count
        selectColumns = rngCell.Columns.Count
        If selectRows <= 0 Or selectColumns < 3 Then
            status = MsgBox("No Selected Area Must be at least one row three columns", vbCritical, "Excel Missing")
        Else
        
        For RowIndex = 1 To selectRows
            NameString = rngCell(RowIndex, 1).Value
            FillColumn = rngCell(RowIndex, 2).Value
            areaValue = rngCell(RowIndex, 3).Value
            Debug.Print " Name: " + NameString + " area: " + Format(areaValue, "0")
            SpaceType = getType(NameString)
            ' Skip Spaces with not Area
            If areaValue > 0 Then
                m_nSpaces = m_nSpaces + 1
                m_SpaceNames(m_nSpaces) = NameString
                m_SpaceArea(m_nSpaces) = areaValue
                m_SpaceType(m_nSpaces) = SpaceType
            End If
        Next RowIndex
        End If

    Exit Sub
ErrorHandle:
        MsgBox "Excel Not running Command Aborted", vbCritical, "Excel Missing"
End Sub

Function getType(NameString As String) As Integer
    Dim i As Integer
    Dim localName As String
    
    localName = Trim(NameString)
    i = InStr(1, localName, " ", vbTextCompare)
    If i = 3 Then
        getType = Building
    ElseIf i = 4 Then
        getType = Gross
    ElseIf i = 6 Then
        getType = Dept
    ElseIf i = 8 Then
        getType = Room
    Else
        getType = Unknown
    End If
End Function

Attribute VB_Name = "main"
Option Explicit

Sub main()
    CommandState.StartPrimitive New PlaceSpaceCommand
End Sub
