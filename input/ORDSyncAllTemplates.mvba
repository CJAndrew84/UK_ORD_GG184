Attribute VB_Name = "LinearEditedSelect"
'   vba Macro to select all EDITED linear templates in current model with library - by Mark Shamoun (21/11/19)


Sub LinearEditedSelect()
    
    Dim oScanEnumerator As ElementEnumerator
    Dim oElement As Element
    Dim ph As PropertyHandler, ph1 As PropertyHandler
    Dim strval0 As String, strval1 As Boolean


'   Scan for edited template drops in current model
    Dim oScanCriteria As New ElementScanCriteria
    oScanCriteria.ExcludeNonGraphical
    oScanCriteria.ExcludeAllClasses
    oScanCriteria.IncludeClass (msdElementClassConstruction)
    
    Set oScanEnumerator = ActiveModelReference.Scan(oScanCriteria)
    
    count = 0
    Do While oScanEnumerator.MoveNext
        Set oElement = oScanEnumerator.Current
        
        Set ph = CreatePropertyHandler(oElement)
        If ph.SelectByAccessString("ElementDescription") = True Then
            strval0 = ph.GetValue
            If Left(strval0, 15) = "Linear Template" Then
                Set ph1 = CreatePropertyHandler(oElement)
                If ph1.SelectByAccessString("TemplateDrop_TemplateEdited") = True Then
                    strval1 = ph1.GetValue
                
                    If strval1 = "True" Then
                        count = count + 1
                        ActiveModelReference.SelectElement oElement
                    End If
                    
                End If
            End If
        End If
    Loop
    
    
'   report status of process
    If count = 0 Then
        CadInputQueue.SendCommand "beep"
        ShowMessage "ERROR - No edited Linear Templates found in current model       (NOTE: A Template Libary must be loaded)", , msdMessageCenterPriorityError, True
    Else
        CadInputQueue.SendCommand "beep"
        ShowMessage Str(count) + " edited Linear Template(s) found", , msdMessageCenterPriorityInfo, False
    End If
    
    
    CommandState.StartDefaultCommand

End Sub

Attribute VB_Name = "LinearSyncAll"
'   vba Macro to synchronise all linear templates in current model with library - by Mark Shamoun (21/11/19)


Sub LinearSyncAll()
    
    Dim oScanEnumerator As ElementEnumerator, oScanEnumerator1 As ElementEnumerator
    Dim oElement As Element, oPoint As Point3d, oView As View, oElement2 As Element
    Dim ph As PropertyHandler, ph1 As PropertyHandler
    Dim strval0 As String, strval1 As Boolean
    Dim strval3 As String, strval4 As Boolean
    Dim skeys As String, Filename As String, sargs As String
    
    
'   read variables to get SendKeys paths
    If ActiveWorkspace.IsConfigurationVariableDefined("CIVIL_LAYERED_STANDARDS_MACRO") = True Then
        cfgVarValue = ActiveWorkspace.ConfigurationVariableValue("CIVIL_LAYERED_STANDARDS_MACRO")
    ElseIf ActiveWorkspace.IsConfigurationVariableDefined("_USTN_WORKSPACESTANDARDS_MACRO") = True Then
        cfgVarValue = ActiveWorkspace.ConfigurationVariableValue("_USTN_WORKSPACESTANDARDS_MACRO")
    ElseIf ActiveWorkspace.IsConfigurationVariableDefined("_USTN_WORKSPACESTANDARDS_MACRO") = True Then
        cfgVarValue = ActiveWorkspace.ConfigurationVariableValue("SENDKEYS_PATH")
    Else
        ShowMessage "WARNING - SendKeys path location not found - Sync will wait to for user input", , msdMessageCenterPriorityWarning
    End If
    
    
'   Check current model
    If ActiveModelReference.IsReadOnly = True Then
        CadInputQueue.SendCommand "beep"
        ShowMessage "ERROR - Current file is Read-Only", , msdMessageCenterPriorityError, True
        CommandState.StartDefaultCommand
        Exit Sub
    ElseIf ActiveModelReference.Is3D = True Then
        CadInputQueue.SendCommand "beep"
        ShowMessage "ERROR - Current model is 3D (Templates Drops reside in 2D model)", , msdMessageCenterPriorityError, True
        CommandState.StartDefaultCommand
        Exit Sub
    End If
    
    
'   Get current view
    For i = 1 To 8
    If ActiveDesignFile.Views(i).IsSelected = True Then
        Set oView = ActiveDesignFile.Views(i)
        Exit For
    End If
    Next
        
        
'   Get key program for dialog response
    Filename = "SendKeys.exe"
    skeys = cfgVarValue + Filename
'   Send Key arguments for Templates edited in place (currently set to simulate spacebar " " - change to "N" to force no update)
    sargs = " 0 3 " + Chr(34) + "WARNING" + Chr(34) + " " + Chr(34) + " " + Chr(34) + " 1"


'   Scan for total linear templates in current model
    Dim oScanCriteria As New ElementScanCriteria
    oScanCriteria.ExcludeNonGraphical
    oScanCriteria.ExcludeAllClasses
    oScanCriteria.IncludeClass (msdElementClassConstruction)

    Set oScanEnumerator1 = ActiveModelReference.Scan(oScanCriteria)

    count1 = 0
    Do While oScanEnumerator1.MoveNext
        Set oElement1 = oScanEnumerator1.Current
        
        Set ph0 = CreatePropertyHandler(oElement1)
        If ph0.SelectByAccessString("ElementDescription") = True Then
            strval3 = ph0.GetValue
            If Left(strval3, 15) = "Linear Template" Then
                count1 = count1 + 1
            End If
        End If
    Loop
    
    If count1 = 0 Then
        GoTo skip
    Else
        ShowTempMessage msdStatusBarAreaMiddle, Str(count1) + "Linear Templates found - Synchonising..."
    End If
    
    
'   Turn on all constructions
    oView.DisplaysConstructions = True
    oView.Redraw
        
    
'   cycle through linear templates in current model and start process
    Set oScanEnumerator = ActiveModelReference.Scan(oScanCriteria)
    
    count = 0
    Do While oScanEnumerator.MoveNext
        ActiveModelReference.UnselectAllElements
        CadInputQueue.SendCommand "displayset clear"
        Set oElement = oScanEnumerator.Current
        
        Set ph = CreatePropertyHandler(oElement)
        If ph.SelectByAccessString("ElementDescription") = True Then
            strval0 = ph.GetValue
            If Left(strval0, 15) = "Linear Template" Then
                Set ph1 = CreatePropertyHandler(oElement)
                count = count + 1
                oVertexList = oElement.ConstructVertexList(0)
                total = UBound(oVertexList)
                oPoint.X = oVertexList(1).X
                oPoint.Y = oVertexList(1).Y
                oPoint.Z = 0
                
                ActiveModelReference.SelectElement oElement
                CadInputQueue.SendCommand "displayset set selection"
                
                If FileExists(skeys) Then
                '   Run SendKeys program to send keypress to answer dialogs (for edited in place templates, not found, etc)
                    Call Shell(Chr(34) + skeys + Chr(34) + sargs, vbNormalFocus)
                End If

                CadInputQueue.SendCommand "corridor template synchronize withlibrary"
                ShowTempMessage msdStatusBarAreaMiddle, "Synchronising" + Str(count) + " of" + Str(count1) + ": " + strval0 + "..."
                CadInputQueue.SendDataPoint oPoint, oView
            End If
        End If
    Loop


skip:

    CadInputQueue.SendCommand "displayset clear"
    CadInputQueue.SendReset
    
    
    ' report status of process
    If count1 = 0 Then
        CadInputQueue.SendCommand "beep"
        ShowMessage "ERROR - No Linear Templates found in current model", , msdMessageCenterPriorityError, True
    ElseIf count = 0 Then
        ShowMessage "UNKNOWN ERROR", , msdMessageCenterPriorityError, True
    Else
        ShowMessage Str(count) + " Linear Template(s) synchronise processes complete", , msdMessageCenterPriorityInfo, True
    End If
    
    
    CommandState.StartDefaultCommand


End Sub
Function FileExists(ByVal strFile As String, Optional bFindFolders As Boolean) As Boolean
    'Purpose:   Return True if the file exists, even if it is hidden.
    'Arguments: strFile: File name to look for. Current directory searched if no path included.
    '           bFindFolders. If strFile is a folder, FileExists() returns False unless this argument is True.
    'Note:      Does not look inside subdirectories for the file.
    'Author:    Allen Browne. http://allenbrowne.com June, 2006.
    Dim lngAttributes As Long

    'Include read-only files, hidden files, system files.
    lngAttributes = (vbReadOnly Or vbHidden Or vbSystem)

    If bFindFolders Then
        lngAttributes = (lngAttributes Or vbDirectory) 'Include folders as well.
    Else
        'Strip any trailing slash, so Dir does not look inside the folder.
        Do While Right$(strFile, 1) = "\"
            strFile = Left$(strFile, Len(strFile) - 1)
        Loop
    End If

    'If Dir() returns something, the file exists.
    On Error Resume Next
    FileExists = (Len(Dir(strFile, lngAttributes)) > 0)
End Function

Function FolderExists(strPath As String) As Boolean
    On Error Resume Next
    FolderExists = ((GetAttr(strPath) And vbDirectory) = vbDirectory)
End Function

Function TrailingSlash(varIn As Variant) As String
    If Len(varIn) > 0 Then
        If Right(varIn, 1) = "\" Then
            TrailingSlash = varIn
        Else
            TrailingSlash = varIn & "\"
        End If
    End If
End Function

Attribute VB_Name = "LinearSyncAllEdited"
'   vba Macro to synchronise all EDITED linear templates in current model with library - by Mark Shamoun (21/11/19)


Sub LinearSyncAllEdited()
    
    Dim oScanEnumerator As ElementEnumerator, oScanEnumerator1 As ElementEnumerator
    Dim oElement As Element, oPoint As Point3d, oView As View, oElement2 As Element
    Dim ph As PropertyHandler, ph1 As PropertyHandler
    Dim strval0 As String, strval1 As Boolean
    Dim strval3 As String, strval4 As Boolean
    Dim skeys As String, Filename As String, sargs As String
    
    
'   read variables to get SendKeys paths
    If ActiveWorkspace.IsConfigurationVariableDefined("CIVIL_LAYERED_STANDARDS_MACRO") = True Then
        cfgVarValue = ActiveWorkspace.ConfigurationVariableValue("CIVIL_LAYERED_STANDARDS_MACRO")
    ElseIf ActiveWorkspace.IsConfigurationVariableDefined("_USTN_WORKSPACESTANDARDS_MACRO") = True Then
        cfgVarValue = ActiveWorkspace.ConfigurationVariableValue("_USTN_WORKSPACESTANDARDS_MACRO")
    ElseIf ActiveWorkspace.IsConfigurationVariableDefined("_USTN_WORKSPACESTANDARDS_MACRO") = True Then
        cfgVarValue = ActiveWorkspace.ConfigurationVariableValue("SENDKEYS_PATH")
    Else
        ShowMessage "WARNING - SendKeys path location not found - Sync will wait to for user input", , msdMessageCenterPriorityWarning
    End If
    
    
'   Check current model
    If ActiveModelReference.IsReadOnly = True Then
        CadInputQueue.SendCommand "beep"
        ShowMessage "ERROR - Current file is Read-Only", , msdMessageCenterPriorityError, True
        CommandState.StartDefaultCommand
        Exit Sub
    ElseIf ActiveModelReference.Is3D = True Then
        CadInputQueue.SendCommand "beep"
        ShowMessage "ERROR - Current model is 3D (Templates Drops reside in 2D model)", , msdMessageCenterPriorityError, True
        CommandState.StartDefaultCommand
        Exit Sub
    End If
    
    
'   Get current view
    For i = 1 To 8
    If ActiveDesignFile.Views(i).IsSelected = True Then
        Set oView = ActiveDesignFile.Views(i)
        Exit For
    End If
    Next
        
        
'   Get key program for dialog response
    Filename = "SendKeys.exe"
    skeys = cfgVarValue + Filename
'   Send Key arguments for Templates edited in place (currently set to simulate spacebar " " - change to "N" to force no update)
    sargs = " 0 3 " + Chr(34) + "WARNING" + Chr(34) + " " + Chr(34) + " " + Chr(34) + " 1"


'   Scan for total edited linear templates in current model
    Dim oScanCriteria As New ElementScanCriteria
    oScanCriteria.ExcludeNonGraphical
    oScanCriteria.ExcludeAllClasses
    oScanCriteria.IncludeClass (msdElementClassConstruction)
    
    Set oScanEnumerator1 = ActiveModelReference.Scan(oScanCriteria)

    count1 = 0
    Do While oScanEnumerator1.MoveNext
        Set oElement1 = oScanEnumerator1.Current
        
        Set ph0 = CreatePropertyHandler(oElement1)
        If ph0.SelectByAccessString("ElementDescription") = True Then
            strval3 = ph0.GetValue
            If Left(strval3, 15) = "Linear Template" Then
                Set ph1 = CreatePropertyHandler(oElement)
                If ph1.SelectByAccessString("TemplateDrop_TemplateEdited") = True Then
                    strval1 = ph1.GetValue
                    If strval1 = "True" Then
                        count1 = count1 + 1
                    End If
                End If
            End If
        End If
    Loop
    
    If count1 = 0 Then
        GoTo skip
    Else
        ShowTempMessage msdStatusBarAreaMiddle, Str(count1) + "Linear Templates found - Synchonising..."
    End If
    
    
'   Turn on all constructions
    oView.DisplaysConstructions = True
    oView.Redraw
    
            
'   cycle through edited linear templates in current model and start process
    Set oScanEnumerator = ActiveModelReference.Scan(oScanCriteria)
    
    count = 0
    Do While oScanEnumerator.MoveNext
        ActiveModelReference.UnselectAllElements
        CadInputQueue.SendCommand "displayset clear"
        Set oElement = oScanEnumerator.Current
        
        Set ph = CreatePropertyHandler(oElement)
        If ph.SelectByAccessString("ElementDescription") = True Then
            strval0 = ph.GetValue
            If Left(strval0, 15) = "Linear Template" Then
                Set ph1 = CreatePropertyHandler(oElement)
                If ph1.SelectByAccessString("TemplateDrop_TemplateEdited") = True Then
                    strval1 = ph1.GetValue
                
                    If strval1 = "True" Then
                        count = count + 1
                        oVertexList = oElement.ConstructVertexList(0)
                        total = UBound(oVertexList)
                        oPoint.X = oVertexList(1).X
                        oPoint.Y = oVertexList(1).Y
                        oPoint.Z = 0
                        
                        ActiveModelReference.SelectElement oElement
                        CadInputQueue.SendCommand "displayset set selection"
                        
                        If FileExists(skeys) Then
                        '   Run SendKeys program to send keypress to answer dialogs (for edited in place templates, not found, etc)
                            Call Shell(Chr(34) + skeys + Chr(34) + sargs, vbNormalFocus)
                        End If

                        CadInputQueue.SendCommand "corridor template synchronize withlibrary"
                        ShowTempMessage msdStatusBarAreaMiddle, "Synchronising" + Str(count) + " of" + Str(count1) + ": " + strval0 + "..."
                        CadInputQueue.SendDataPoint oPoint, oView
                    End If
                End If
            End If
        End If
    Loop
    
    
    CadInputQueue.SendCommand "displayset clear"
    
    
'   Rescan for edited template drops in current model for confirmation
    If count > 0 Then
    Set oScanEnumerator1 = ActiveModelReference.Scan(oScanCriteria)

    count1 = 0
    Do While oScanEnumerator1.MoveNext
        Set oElement1 = oScanEnumerator1.Current
        
        Set ph0 = CreatePropertyHandler(oElement1)
        If ph0.SelectByAccessString("ElementDescription") = True Then
            strval3 = ph0.GetValue
            If Left(strval3, 15) = "Linear Template" Then
                Set ph01 = CreatePropertyHandler(oElement1)
                If ph01.SelectByAccessString("TemplateDrop_TemplateEdited") = True Then
                    strval4 = ph01.GetValue
                    If strval4 = "True" Then
                        count1 = count1 + 1
                    End If
                End If
            End If
        End If
    Loop
    End If


    CadInputQueue.SendCommand "displayset clear"
    CadInputQueue.SendReset
    
    
skip:
    
    ' report status of process
    If count1 = 0 Then
        CadInputQueue.SendCommand "beep"
        ShowMessage "ERROR - No edited Linear Templates found in current model     (NOTE: A Template Libary must be loaded)", , msdMessageCenterPriorityError, True
    ElseIf count2 = 0 Then
        CadInputQueue.SendCommand "beep"
        ShowMessage Str(count) + " edited Linear Template(s) successfully synchronised with Template Library", , msdMessageCenterPriorityInfo, True
    ElseIf count2 < count Then
        ShowMessage Str(count - count2) + " edited Linear Template(s) successfully synchronised with Template Library (" + Str(count2) + " failed )", , msdMessageCenterPriorityWarning, True
    ElseIf count = count2 Then
        ShowMessage "ERROR - No edited Linear Templates synchronised with Template Library (" + Str(count2) + " failed )", , msdMessageCenterPriorityError, True
    Else
        ShowMessage "UNKNOWN ERROR", , msdMessageCenterPriorityError, True
    End If
    
    
    CommandState.StartDefaultCommand


End Sub
Function FileExists(ByVal strFile As String, Optional bFindFolders As Boolean) As Boolean
    'Purpose:   Return True if the file exists, even if it is hidden.
    'Arguments: strFile: File name to look for. Current directory searched if no path included.
    '           bFindFolders. If strFile is a folder, FileExists() returns False unless this argument is True.
    'Note:      Does not look inside subdirectories for the file.
    'Author:    Allen Browne. http://allenbrowne.com June, 2006.
    Dim lngAttributes As Long

    'Include read-only files, hidden files, system files.
    lngAttributes = (vbReadOnly Or vbHidden Or vbSystem)

    If bFindFolders Then
        lngAttributes = (lngAttributes Or vbDirectory) 'Include folders as well.
    Else
        'Strip any trailing slash, so Dir does not look inside the folder.
        Do While Right$(strFile, 1) = "\"
            strFile = Left$(strFile, Len(strFile) - 1)
        Loop
    End If

    'If Dir() returns something, the file exists.
    On Error Resume Next
    FileExists = (Len(Dir(strFile, lngAttributes)) > 0)
End Function

Function FolderExists(strPath As String) As Boolean
    On Error Resume Next
    FolderExists = ((GetAttr(strPath) And vbDirectory) = vbDirectory)
End Function

Function TrailingSlash(varIn As Variant) As String
    If Len(varIn) > 0 Then
        If Right(varIn, 1) = "\" Then
            TrailingSlash = varIn
        Else
            TrailingSlash = varIn & "\"
        End If
    End If
End Function

Attribute VB_Name = "TemplateEditedSelect"
'   vba Macro to select all EDITED ORD template drops in current model with library - by Mark Shamoun (21/11/19)


Sub TemplateEditedSelect()
    
    Dim oScanEnumerator As ElementEnumerator
    Dim oElement As Element
    Dim ph As PropertyHandler, ph1 As PropertyHandler
    Dim strval0 As String, strval1 As Boolean

            
'   Scan for edited template drops in current model
    Dim oScanCriteria As New ElementScanCriteria
    oScanCriteria.ExcludeNonGraphical
    oScanCriteria.ExcludeAllClasses
    oScanCriteria.IncludeClass (msdElementClassConstruction)
    
    Set oScanEnumerator = ActiveModelReference.Scan(oScanCriteria)
    
    count = 0
    Do While oScanEnumerator.MoveNext
        Set oElement = oScanEnumerator.Current
        
        Set ph = CreatePropertyHandler(oElement)
        If ph.SelectByAccessString("ElementDescription") = True Then
            strval0 = ph.GetValue
            If Left(strval0, 13) = "Template Drop" Then
                Set ph1 = CreatePropertyHandler(oElement)
                If ph1.SelectByAccessString("TemplateDrop_TemplateEdited") = True Then
                    strval1 = ph1.GetValue
                
                    If strval1 = "True" Then
                        count = count + 1
                        ActiveModelReference.SelectElement oElement
                    End If
                    
                End If
            End If
        End If
    Loop
    
    
    
'   report status of process
    If count = 0 Then
        CadInputQueue.SendCommand "beep"
        ShowMessage "ERROR - No edited Template Drops found in current model       (NOTE: A Template Libary must be loaded)", , msdMessageCenterPriorityError, True
    Else
        CadInputQueue.SendCommand "beep"
        ShowMessage Str(count) + " edited Template Drop(s) found", , msdMessageCenterPriorityInfo, False
    End If
    
    
    CommandState.StartDefaultCommand

End Sub

Attribute VB_Name = "TemplateSyncAll"
'   vba Macro to synchronise all ORD template drops in current model with library - by Mark Shamoun (21/11/19)


Sub TempateSyncAll()
    
    Dim oScanEnumerator As ElementEnumerator, oScanEnumerator1 As ElementEnumerator
    Dim oElement As Element, oPoint As Point3d, oView As View, oElement2 As Element
    Dim ph As PropertyHandler, ph1 As PropertyHandler
    Dim strval0 As String, strval1 As Boolean
    Dim strval3 As String, strval4 As Boolean
    Dim skeys As String, Filename As String, sargs As String
    
    
'   read variables to get SendKeys paths
    If ActiveWorkspace.IsConfigurationVariableDefined("CIVIL_LAYERED_STANDARDS_MACRO") = True Then
        cfgVarValue = ActiveWorkspace.ConfigurationVariableValue("CIVIL_LAYERED_STANDARDS_MACRO")
    ElseIf ActiveWorkspace.IsConfigurationVariableDefined("_USTN_WORKSPACESTANDARDS_MACRO") = True Then
        cfgVarValue = ActiveWorkspace.ConfigurationVariableValue("_USTN_WORKSPACESTANDARDS_MACRO")
    ElseIf ActiveWorkspace.IsConfigurationVariableDefined("_USTN_WORKSPACESTANDARDS_MACRO") = True Then
        cfgVarValue = ActiveWorkspace.ConfigurationVariableValue("SENDKEYS_PATH")
    Else
        ShowMessage "WARNING - SendKeys path location not found - Sync will wait to for user input", , msdMessageCenterPriorityWarning
    End If
    
        
'   Check current model
    If ActiveModelReference.IsReadOnly = True Then
        CadInputQueue.SendCommand "beep"
        ShowMessage "ERROR - Current file is Read-Only", , msdMessageCenterPriorityError, True
        CommandState.StartDefaultCommand
        Exit Sub
    ElseIf ActiveModelReference.Is3D = True Then
        CadInputQueue.SendCommand "beep"
        ShowMessage "ERROR - Current model is 3D (Templates Drops reside in 2D model)", , msdMessageCenterPriorityError, True
        CommandState.StartDefaultCommand
        Exit Sub
    End If
    
    
'   Get current view
    For i = 1 To 8
    If ActiveDesignFile.Views(i).IsSelected = True Then
        Set oView = ActiveDesignFile.Views(i)
        Exit For
    End If
    Next
        
        
'   Get key program for dialog response
    Filename = "SendKeys.exe"
    skeys = cfgVarValue + Filename
'   Send Key arguments for Templates edited in place (currently set to simulate spacebar " " - change to "N" to force no update)
    sargs = " 0 3 " + Chr(34) + "WARNING" + Chr(34) + " " + Chr(34) + " " + Chr(34) + " 1"
    
            
'   Scan for total template drops in current model
    Dim oScanCriteria As New ElementScanCriteria
    oScanCriteria.ExcludeNonGraphical
    oScanCriteria.ExcludeAllClasses
    oScanCriteria.IncludeClass (msdElementClassConstruction)
    
    Set oScanEnumerator1 = ActiveModelReference.Scan(oScanCriteria)

    count1 = 0
    Do While oScanEnumerator1.MoveNext
        Set oElement1 = oScanEnumerator1.Current
        
        Set ph0 = CreatePropertyHandler(oElement1)
        If ph0.SelectByAccessString("ElementDescription") = True Then
            strval3 = ph0.GetValue
            If Left(strval3, 13) = "Template Drop" Then
                count1 = count1 + 1
            End If
        End If
    Loop
    
    If count1 = 0 Then
        GoTo skip
    Else
        ShowTempMessage msdStatusBarAreaMiddle, Str(count1) + "Template Drops found - Synchonising..."
    End If
    
    
'   Turn on all constructions
    oView.DisplaysConstructions = True
    oView.Redraw
    
    
'   cycle through all template drops in current model and start process
    Set oScanEnumerator = ActiveModelReference.Scan(oScanCriteria)
    
    warn = 0
    count = 0
    Do While oScanEnumerator.MoveNext
        ActiveModelReference.UnselectAllElements
        CadInputQueue.SendCommand "displayset clear"
        Set oElement = oScanEnumerator.Current
        
        Set ph = CreatePropertyHandler(oElement)
        If ph.SelectByAccessString("ElementDescription") = True Then
            strval0 = ph.GetValue
            If Left(strval0, 13) = "Template Drop" Then
                Set ph1 = CreatePropertyHandler(oElement)
                count = count + 1
                oVertexList = oElement.ConstructVertexList(0)
                total = UBound(oVertexList)
                oPoint.X = oVertexList(1).X
                oPoint.Y = oVertexList(1).Y
                oPoint.Z = 0
                
                ActiveModelReference.SelectElement oElement
                CadInputQueue.SendCommand "displayset set selection"
                
                If FileExists(skeys) Then
                '   Run SendKeys program to send keypress to answer dialogs (for edited in place templates, not found, etc)
                    Call Shell(Chr(34) + skeys + Chr(34) + sargs, vbNormalFocus)
                Else
                    If warn = 0 Then
                        ShowMessage "WARNING - SendKeys application not found - Sync will wait to for user input", , msdMessageCenterPriorityWarning
                        warn = 1
                    End If
                End If

                CadInputQueue.SendCommand "corridor template synchronize withlibrary"
                ShowTempMessage msdStatusBarAreaMiddle, "Synchronising" + Str(count) + " of" + Str(count1) + ": " + strval0 + "..."
                CadInputQueue.SendDataPoint oPoint, oView
            End If
        End If
    Loop


skip:

    CadInputQueue.SendCommand "displayset clear"
    CadInputQueue.SendReset
    
    
    ' report status of process
    If count1 = 0 Then
        CadInputQueue.SendCommand "beep"
        ShowMessage "ERROR - No Template Drops found in current model", , msdMessageCenterPriorityError, True
    ElseIf count = 0 Then
        ShowMessage "UNKNOWN ERROR", , msdMessageCenterPriorityError, True
    Else
        ShowMessage Str(count) + " Template Drop(s) synchronise processes complete", , msdMessageCenterPriorityInfo, True
    End If


    CommandState.StartDefaultCommand


End Sub
Function FileExists(ByVal strFile As String, Optional bFindFolders As Boolean) As Boolean
    'Purpose:   Return True if the file exists, even if it is hidden.
    'Arguments: strFile: File name to look for. Current directory searched if no path included.
    '           bFindFolders. If strFile is a folder, FileExists() returns False unless this argument is True.
    'Note:      Does not look inside subdirectories for the file.
    'Author:    Allen Browne. http://allenbrowne.com June, 2006.
    Dim lngAttributes As Long

    'Include read-only files, hidden files, system files.
    lngAttributes = (vbReadOnly Or vbHidden Or vbSystem)

    If bFindFolders Then
        lngAttributes = (lngAttributes Or vbDirectory) 'Include folders as well.
    Else
        'Strip any trailing slash, so Dir does not look inside the folder.
        Do While Right$(strFile, 1) = "\"
            strFile = Left$(strFile, Len(strFile) - 1)
        Loop
    End If

    'If Dir() returns something, the file exists.
    On Error Resume Next
    FileExists = (Len(Dir(strFile, lngAttributes)) > 0)
End Function

Function FolderExists(strPath As String) As Boolean
    On Error Resume Next
    FolderExists = ((GetAttr(strPath) And vbDirectory) = vbDirectory)
End Function

Function TrailingSlash(varIn As Variant) As String
    If Len(varIn) > 0 Then
        If Right(varIn, 1) = "\" Then
            TrailingSlash = varIn
        Else
            TrailingSlash = varIn & "\"
        End If
    End If
End Function

Attribute VB_Name = "TemplateSyncAllEdited"
'   vba Macro to synchronise all EDITED template drops in current model with library - by Mark Shamoun (21/11/19)


Sub TemplateSyncAllEdited()
    
    Dim oScanEnumerator As ElementEnumerator, oScanEnumerator1 As ElementEnumerator
    Dim oElement As Element, oPoint As Point3d, oView As View, oElement2 As Element
    Dim ph As PropertyHandler, ph1 As PropertyHandler
    Dim strval0 As String, strval1 As Boolean
    Dim strval3 As String, strval4 As Boolean
    Dim skeys As String, Filename As String, sargs As String
    
    
'   read variables to get SendKeys paths
    If ActiveWorkspace.IsConfigurationVariableDefined("CIVIL_LAYERED_STANDARDS_MACRO") = True Then
        cfgVarValue = ActiveWorkspace.ConfigurationVariableValue("CIVIL_LAYERED_STANDARDS_MACRO")
    ElseIf ActiveWorkspace.IsConfigurationVariableDefined("_USTN_WORKSPACESTANDARDS_MACRO") = True Then
        cfgVarValue = ActiveWorkspace.ConfigurationVariableValue("_USTN_WORKSPACESTANDARDS_MACRO")
    ElseIf ActiveWorkspace.IsConfigurationVariableDefined("_USTN_WORKSPACESTANDARDS_MACRO") = True Then
        cfgVarValue = ActiveWorkspace.ConfigurationVariableValue("SENDKEYS_PATH")
    Else
        ShowMessage "WARNING - SendKeys path location not found - Sync will wait to for user input", , msdMessageCenterPriorityWarning
    End If
    
    
'   Check current model
    If ActiveModelReference.IsReadOnly = True Then
        CadInputQueue.SendCommand "beep"
        ShowMessage "ERROR - Current file is Read-Only", , msdMessageCenterPriorityError, True
        CommandState.StartDefaultCommand
        Exit Sub
    ElseIf ActiveModelReference.Is3D = True Then
        CadInputQueue.SendCommand "beep"
        ShowMessage "ERROR - Current model is 3D (Template Drops reside in 2D model)", , msdMessageCenterPriorityError, True
        CommandState.StartDefaultCommand
        Exit Sub
    End If
    
    
'   Get current view
    For i = 1 To 8
    If ActiveDesignFile.Views(i).IsSelected = True Then
        Set oView = ActiveDesignFile.Views(i)
        Exit For
    End If
    Next
        
        
'   Get key program for dialog response
    Filename = "SendKeys.exe"
    skeys = cfgVarValue + Filename
'   Send Key arguments for Templates edited in place (currently set to simulate spacebar " " - change to "N" to force no update)
    sargs = " 0 3 " + Chr(34) + "WARNING" + Chr(34) + " " + Chr(34) + " " + Chr(34) + " 1"
   

'   Scan for total edited template drops in current model
    Dim oScanCriteria As New ElementScanCriteria
    oScanCriteria.ExcludeNonGraphical
    oScanCriteria.ExcludeAllClasses
    oScanCriteria.IncludeClass (msdElementClassConstruction)
    
    Set oScanEnumerator1 = ActiveModelReference.Scan(oScanCriteria)

    count1 = 0
    Do While oScanEnumerator1.MoveNext
        Set oElement1 = oScanEnumerator1.Current
        
        Set ph0 = CreatePropertyHandler(oElement1)
        If ph0.SelectByAccessString("ElementDescription") = True Then
            strval3 = ph0.GetValue
            If Left(strval3, 13) = "Template Drop" Then
                Set ph1 = CreatePropertyHandler(oElement1)
                If ph1.SelectByAccessString("TemplateDrop_TemplateEdited") = True Then
                    strval1 = ph1.GetValue
                    If strval1 = "True" Then
                        count1 = count1 + 1
                    End If
                End If
            End If
        End If
    Loop
    
    If count1 = 0 Then
        GoTo skip
    Else
        ShowTempMessage msdStatusBarAreaMiddle, Str(count1) + "Template Drops found - Synchonising..."
    End If
    
    
    
'   Turn on all constructions
    oView.DisplaysConstructions = True
    oView.Redraw
    
            
'   cycle through all edited template drops in current model and start process
    Set oScanEnumerator = ActiveModelReference.Scan(oScanCriteria)
    
    warn = 0
    count = 0
    Do While oScanEnumerator.MoveNext
        ActiveModelReference.UnselectAllElements
        CadInputQueue.SendCommand "displayset clear"
        Set oElement = oScanEnumerator.Current
        
        Set ph = CreatePropertyHandler(oElement)
        If ph.SelectByAccessString("ElementDescription") = True Then
            strval0 = ph.GetValue
            If Left(strval0, 13) = "Template Drop" Then
                Set ph1 = CreatePropertyHandler(oElement)
                If ph1.SelectByAccessString("TemplateDrop_TemplateEdited") = True Then
                    strval1 = ph1.GetValue
                
                    If strval1 = "True" Then
                        count = count + 1
                        oVertexList = oElement.ConstructVertexList(0)
                        total = UBound(oVertexList)
                        oPoint.X = oVertexList(1).X
                        oPoint.Y = oVertexList(1).Y
                        oPoint.Z = 0
                        
                        ActiveModelReference.SelectElement oElement
                        CadInputQueue.SendCommand "displayset set selection"
                        
                        If FileExists(skeys) Then
                        '   Run SendKeys program to send keypress to answer dialogs (for edited in place templates, not found, etc)
                            Call Shell(Chr(34) + skeys + Chr(34) + sargs, vbNormalFocus)
                        Else
                            If warn = 0 Then
                                ShowMessage "WARNING - SendKeys application not found - Sync will wait to for user input", , msdMessageCenterPriorityWarning
                                warn = 1
                            End If
                        End If
    
                        CadInputQueue.SendCommand "corridor template synchronize withlibrary"
                        ShowTempMessage msdStatusBarAreaMiddle, "Synchronising" + Str(count) + " of" + Str(count1) + ": " + strval0 + "..."
                        CadInputQueue.SendDataPoint oPoint, oView
                    End If
                End If
            End If
        End If
    Loop
    
    CadInputQueue.SendCommand "displayset clear"


'   Rescan for edited template drops in current model for confirmation
    If count > 0 Then
        Set oScanEnumerator1 = ActiveModelReference.Scan(oScanCriteria)
    
        count2 = 0
        Do While oScanEnumerator1.MoveNext
            Set oElement1 = oScanEnumerator1.Current
            
            Set ph0 = CreatePropertyHandler(oElement1)
            If ph0.SelectByAccessString("ElementDescription") = True Then
                strval3 = ph0.GetValue
                If Left(strval3, 13) = "Template Drop" Then
                    Set ph01 = CreatePropertyHandler(oElement1)
                    If ph01.SelectByAccessString("TemplateDrop_TemplateEdited") = True Then
                        strval4 = ph01.GetValue
                        If strval4 = "True" Then
                            count2 = count2 + 1
                        End If
                    End If
                End If
            End If
        Loop
    End If



skip:

    CadInputQueue.SendCommand "displayset clear"
    CadInputQueue.SendReset
    
    
    ' report status of process
    If count1 = 0 Then
        CadInputQueue.SendCommand "beep"
        ShowMessage "ERROR - No edited Template Drops found in current model     (NOTE: A Template Libary must be loaded)", , msdMessageCenterPriorityError, True
    ElseIf count2 = 0 Then
        CadInputQueue.SendCommand "beep"
        ShowMessage Str(count) + " edited Template Drop(s) successfully synchronised with Template Library", , msdMessageCenterPriorityInfo, True
    ElseIf count2 < count Then
        ShowMessage Str(count - count2) + " edited Template Drop(s) successfully synchronised with Template Library (" + Str(count2) + " failed )", , msdMessageCenterPriorityWarning, True
    ElseIf count = count2 Then
        ShowMessage "ERROR - No edited Template Drops synchronised with Template Library (" + Str(count2) + " failed )", , msdMessageCenterPriorityError, True
    Else
        ShowMessage "UNKNOWN ERROR", , msdMessageCenterPriorityError, True
    End If


    CommandState.StartDefaultCommand


End Sub
Function FileExists(ByVal strFile As String, Optional bFindFolders As Boolean) As Boolean
    'Purpose:   Return True if the file exists, even if it is hidden.
    'Arguments: strFile: File name to look for. Current directory searched if no path included.
    '           bFindFolders. If strFile is a folder, FileExists() returns False unless this argument is True.
    'Note:      Does not look inside subdirectories for the file.
    'Author:    Allen Browne. http://allenbrowne.com June, 2006.
    Dim lngAttributes As Long

    'Include read-only files, hidden files, system files.
    lngAttributes = (vbReadOnly Or vbHidden Or vbSystem)

    If bFindFolders Then
        lngAttributes = (lngAttributes Or vbDirectory) 'Include folders as well.
    Else
        'Strip any trailing slash, so Dir does not look inside the folder.
        Do While Right$(strFile, 1) = "\"
            strFile = Left$(strFile, Len(strFile) - 1)
        Loop
    End If

    'If Dir() returns something, the file exists.
    On Error Resume Next
    FileExists = (Len(Dir(strFile, lngAttributes)) > 0)
End Function

Function FolderExists(strPath As String) As Boolean
    On Error Resume Next
    FolderExists = ((GetAttr(strPath) And vbDirectory) = vbDirectory)
End Function

Function TrailingSlash(varIn As Variant) As String
    If Len(varIn) > 0 Then
        If Right(varIn, 1) = "\" Then
            TrailingSlash = varIn
        Else
            TrailingSlash = varIn & "\"
        End If
    End If
End Function
