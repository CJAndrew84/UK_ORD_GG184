Attribute VB_Name = "GetDPLocation"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

' Implement Statement: inform MicroStation that a class is going to provide code for the IPrimitiveCommandEvents interface
Implements IPrimitiveCommandEvents

Public ZScale As Double
Public AttInx As Long

Private Sub IPrimitiveCommandEvents_Cleanup()
  
  ' Clear out the MicroStation prompts
  ShowCommand ""
  ShowPrompt ""

End Sub

Private Sub IPrimitiveCommandEvents_DataPoint(point As Point3d, ByVal view As view)

  Dim mtrxScale As Matrix3d
  Dim mtrxCombined As Matrix3d
  Dim trns As Transform3d
  
  '  Create a scaling matrix
  mtrxScale = Matrix3dFromScaleFactors(1, 1, ZScale)
  
  ' Multiply the matrices to create a matrix that scales and rotates
  mtrxCombined = Matrix3dFromMatrix3dTimesMatrix3d(Matrix3dIdentity, mtrxScale)
  
  '  Create a transform to rotate and scale about a fixed point
  trns = Transform3dFromMatrix3dAndFixedPoint3d(mtrxCombined, point)

  ' Apply the transform to the attachment
  ActiveModelReference.Attachments(AttInx).Transform trns, True
  ActiveModelReference.Attachments(AttInx).Rewrite

  ' Back to default state
  CommandState.StartDefaultCommand
  
  ' Refresh the view
  CursorInformation.CurrentView.Redraw

End Sub

Private Sub IPrimitiveCommandEvents_Dynamics(point As Point3d, ByVal view As view, ByVal DrawMode As MsdDrawingMode)

End Sub

Private Sub IPrimitiveCommandEvents_Keyin(ByVal Keyin As String)

End Sub

Private Sub IPrimitiveCommandEvents_Reset() ' method called when the reset event occurs

  ' Set MicroStation to the default command state
  CommandState.StartDefaultCommand

End Sub

Private Sub IPrimitiveCommandEvents_Start() 'method called at the start of the command
  
  'Provide command and prompt user for required input
  ShowCommand "Exaggerate Z: "

  ShowPrompt "DP Point to scale about"

  ' Turn accusnap on
  CommandState.EnableAccuSnap

End Sub

Attribute VB_Name = "ModalDlgHandler"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements IModalDialogEvents

Private Sub IModalDialogEvents_OnDialogClosed(ByVal DialogBoxName As String, ByVal DialogResult As MsdDialogBoxResult)

End Sub

Private Sub IModalDialogEvents_OnDialogOpened(ByVal DialogBoxName As String, DialogResult As MsdDialogBoxResult)

  If DialogBoxName Like "Preferences*" Then
    Dim vwCurr As view

    ' Get the current setting
    Dim intToggle As Integer
    intToggle = GetCExpressionValue("savePrefs.flags.invertBackground", "USERPREF")

    If intToggle = 0 Then
      ' Black background so turn white
      SetCExpressionValue "savePrefs.flags.invertBackground", 1, "USERPREF"
      ' Turn ON Symbology Override in all views
      For Each vwCurr In ActiveDesignFile.Views
        vwCurr.DisplaysLevelSymbology = True
      Next vwCurr
    Else
      ' White background so turn black
      SetCExpressionValue "savePrefs.flags.invertBackground", 0, "USERPREF"
      ' Turn OFF Symbology Override
      For Each vwCurr In ActiveDesignFile.Views
        vwCurr.DisplaysLevelSymbology = False
      Next vwCurr
    End If

    ' Close the dialog box.
    DialogResult = msdDialogBoxResultOK

  End If  ' Preferences [untitled]

End Sub

Attribute VB_Name = "Module1"
Option Explicit

'Declare PtrSafe Function mdlRefFile_getInfo Lib "stdmdlbltin.dll" (ByVal modelRef As LongLong) As LongPtr   ' Returns a pointer to a structure

Sub AccuDrawToggleOnOff()
       
    If MicroStationDGN.CommandState.AccuDrawHints.IsEnabled = True Then
 
        CadInputQueue.SendKeyin "accudraw activate"
        
        CadInputQueue.SendCommand "DMSG ACTIVATETOOLBYPATH Civil AccuDraw\Toggle Civil AccuDraw"
    
        CadInputQueue.SendCommand "CIVILCOORD ACTIVATE "
    
    Else

        CadInputQueue.SendCommand "DMSG ACTIVATETOOLBYPATH Civil AccuDraw\Toggle Civil AccuDraw"
    
        CadInputQueue.SendCommand "CIVILCOORD QUIT "
            
        CadInputQueue.SendKeyin "accudraw activate"
    
    End If
    

End Sub


Sub Toggle()

  ' Add the handler for the preferences dialog
  Dim modalHandler As New ModalDlgHandler
  AddModalDialogEventsHandler modalHandler

  ' The following statement opens modal dialog "Preferences [untitled]"
  ' The handler does the work
  CadInputQueue.SendCommand "MDL SILENTLOAD USERPREF"

  ' Cleanup
  RemoveModalDialogEventsHandler modalHandler
  CommandState.StartDefaultCommand

End Sub


Sub OneView()

  ActiveDesignFile.Views(1).IsOpen = True
  
  ' Close the rest
  Dim i As Integer
  For i = 2 To 8
    ActiveDesignFile.Views(i).IsOpen = False
  Next i
  CadInputQueue.SendKeyin "view set model ""Default"" 1"
  ActiveDesignFile.Views(1).Maximize

End Sub

Sub TwoView()

  ActiveDesignFile.Views(1).IsOpen = True
  ActiveDesignFile.Views(2).IsOpen = True

  ' Close the rest
  Dim i As Integer
  For i = 3 To 8
    ActiveDesignFile.Views(i).IsOpen = False
  Next i

  ' Panel the views (maximize first so ARRANGE will make them horizontal)
  ActiveDesignFile.Views(2).Maximize
  ActiveDesignFile.Views(1).Maximize
  CadInputQueue.SendCommand "WINDOW TILE"
  CadInputQueue.SendCommand "FIT VIEW EXTENDED 2"
  ActiveDesignFile.Views(1).Select
  CadInputQueue.SendKeyin "view set model ""Default"" 1"
  CadInputQueue.SendCommand "FIT VIEW EXTENDED 1"
  CadInputQueue.SendCommand "CHOOSE NONE"
     

End Sub

Sub FourView()
' Close views 2-8
  Dim i As Integer
  For i = 2 To 8
    ActiveDesignFile.Views(i).IsOpen = False
  Next i
  
  ' Open Views 1,3,4 and 7.  1 = Plan, 3 = 3D Model, 5 = Profile, 7 = XS
  ActiveDesignFile.Views(1).IsOpen = True
  ActiveDesignFile.Views(1).Maximize
  CadInputQueue.SendKeyin "view set model ""Default"" 1"
  ActiveDesignFile.Views(3).IsOpen = True
  ActiveDesignFile.Views(5).IsOpen = True
  ActiveDesignFile.Views(7).IsOpen = True
  CadInputQueue.SendKeyin "MDL KEYIN BENTLEY.VIEWATTRIBUTESDIALOG,VAD VIEWATTRIBUTESDIALOG SETATTRIBUTE 4 Grid True"
  CadInputQueue.SendKeyin "MDL KEYIN BENTLEY.VIEWATTRIBUTESDIALOG,VAD VIEWATTRIBUTESDIALOG SETATTRIBUTE 6 Grid True"
    
  ' Try to find the 3D model for the active model and assign to View 3
  Dim strModName3D As String
  strModName3D = ActiveModelReference.name & "-3D"
  Dim blnFound As Boolean
  blnFound = False
  Dim modRefCurr As ModelReference
  For Each modRefCurr In ActiveDesignFile.Models
    If UCase(modRefCurr.name) = UCase(strModName3D) Then
      ' Found it
      blnFound = True
      CadInputQueue.SendKeyin "view set model """ & modRefCurr.name & """ 3"
    ' Stop looking
      Exit For
    End If
  Next modRefCurr
  If Not blnFound Then
    ' Didn't find the standard one so set view 3 to the first "*-3D" model found
    For Each modRefCurr In ActiveDesignFile.Models
      If UCase(Right(modRefCurr.name, 3)) = "-3D" Then
        ' Found one so use it
        blnFound = True
        CadInputQueue.SendKeyin "view set model """ & modRefCurr.name & """ 3"
      ' Stop looking
        Exit For
      End If
    Next modRefCurr
  End If
  If Not blnFound Then
    ' Didn't find a model with "-3D" at the end so set view 3 to the first 3D model found
    For Each modRefCurr In ActiveDesignFile.Models
      If modRefCurr.Is3D Then
        ' Found one so use it
        blnFound = True
        CadInputQueue.SendKeyin "view set model """ & modRefCurr.name & """ 3"
      ' Stop looking
        Exit For
      End If
    Next modRefCurr
  End If

  ' Set view 3 to Smooth
  ' CadInputQueue.SendKeyin "CHANGE VIEW CUSTOM ""Smooth"" 3"
  CadInputQueue.SendKeyin "CHANGE VIEW CUSTOM ""Illustration:Ignore Lighting"" 3"
  CadInputQueue.SendKeyin "MDL KEYIN BENTLEY.VIEWATTRIBUTESDIALOG,VAD VIEWATTRIBUTESDIALOG SETATTRIBUTE 3 ClipVolume False "
  CadInputQueue.SendCommand "WINDOW TILE"

  ' Set view 3 to the same range as view 1
  ActiveDesignFile.Views(1).Select
  Dim vwOne As view
  Set vwOne = ActiveDesignFile.Views(1)
  Dim vwTwo As view
  Set vwTwo = ActiveDesignFile.Views(3)
  vwTwo.Rotation = Matrix3dIdentity
  On Error Resume Next
  vwTwo.Fit True
  On Error GoTo 0
  ' Adjust extents and origin for 3D
  Dim pntExtents As Point3d
  pntExtents = vwOne.Extents
  pntExtents.Z = vwTwo.Extents.Z
  Dim pntOrigin As Point3d
  pntOrigin = vwOne.Origin
  pntOrigin.Z = vwTwo.Origin.Z
  vwTwo.SetArea pntOrigin, pntExtents, vwOne.Rotation, vwOne.ActiveDepth
  ' Get the average element elevation in the view and set the center to that
  Dim dblAvgElev As Double
  dblAvgElev = GetViewElementsAverageElevation(vwTwo)
  ' Rotate up 60 degrees about the X axis
  vwTwo.Rotation = Matrix3dFromAxisAndRotationAngle(0, -1 * Pi / 3)
  vwTwo.Center = Point3dFromXYZ(vwOne.Center.X, vwOne.Center.Y, dblAvgElev)
  
  vwTwo.ClipVolume = True
  vwTwo.ClipFront = False
  vwTwo.ClipBack = False
  
  vwTwo.Redraw
  ActiveDesignFile.Views(3).Select
  
  ' Make View 1 active
  ActiveDesignFile.Views(1).Select
  CadInputQueue.SendCommand "UPDATE VIEW EXTENDED 1"
  CadInputQueue.SendCommand "CHOOSE NONE"
  
    
 'Execute the Open Profile Model Command
  Dim dlgResult As VbMsgBoxResult
  dlgResult = MsgBox("Select OK to Create a Dynamic Profile View", vbOKCancel, "Open a Dynamic Profile View")
  If dlgResult = 1 Then
    Call OpenProfileModel
  End If
  
  
  'Execute the Open DynamicXS Model Command
   dlgResult = MsgBox("Select OK to Create a Dynamic XS View", vbOKCancel, "Open a Dynamic Cross Section View")
   If dlgResult = 1 Then
     Call OpenDynamicXSModel
   End If


End Sub

Sub TwoView3D()

  ActiveDesignFile.Views(1).IsOpen = True
  ActiveDesignFile.Views(2).IsOpen = True

  ' Close the rest
  Dim i As Integer
  For i = 3 To 8
    ActiveDesignFile.Views(i).IsOpen = False
  Next i

  ' Panel the views (maximize first so TILE will make them side-by-side)
  ActiveDesignFile.Views(2).Maximize
  ActiveDesignFile.Views(1).Maximize
  CadInputQueue.SendKeyin "view set model ""Default"" 1"
  CadInputQueue.SendCommand "WINDOW TILE"
  
  
  ' Try to find the 3D model for the active model
  Dim strModName3D As String
  strModName3D = ActiveModelReference.name & "-3D"
  Dim blnFound As Boolean
  blnFound = False
  Dim modRefCurr As ModelReference
  For Each modRefCurr In ActiveDesignFile.Models
    If UCase(modRefCurr.name) = UCase(strModName3D) Then
      ' Found it
      blnFound = True
      CadInputQueue.SendKeyin "view set model """ & modRefCurr.name & """ 2"
      CadInputQueue.SendCommand "WINDOW TILE"
      ' Stop looking
      Exit For
    End If
  Next modRefCurr
  If Not blnFound Then
    ' Didn't find the standard one so set view 2 to the first "*-3D" model found
    For Each modRefCurr In ActiveDesignFile.Models
      If UCase(Right(modRefCurr.name, 3)) = "-3D" Then
        ' Found one so use it
        blnFound = True
        CadInputQueue.SendKeyin "view set model """ & modRefCurr.name & """ 2"
        CadInputQueue.SendCommand "WINDOW TILE"
        ' Stop looking
        Exit For
      End If
    Next modRefCurr
  End If
  If Not blnFound Then
    ' Didn't find a model with "-3D" at the end so set view 2 to the first 3D model found
    For Each modRefCurr In ActiveDesignFile.Models
      If modRefCurr.Is3D Then
        ' Found one so use it
        blnFound = True
        CadInputQueue.SendKeyin "view set model """ & modRefCurr.name & """ 2"
        CadInputQueue.SendCommand "WINDOW TILE"
        ' Stop looking
        Exit For
      End If
    Next modRefCurr
  End If

  ' Set view 2 to Smooth
  ' CadInputQueue.SendKeyin "CHANGE VIEW CUSTOM ""Smooth"" 2"
  CadInputQueue.SendKeyin "CHANGE VIEW CUSTOM ""Illustration:Ignore Lighting"" 2"
  CadInputQueue.SendKeyin "MDL KEYIN BENTLEY.VIEWATTRIBUTESDIALOG,VAD VIEWATTRIBUTESDIALOG SETATTRIBUTE 2 ClipVolume False "

  ' Set view 2 to the same range as view 1
  Dim vwOne As view
  Set vwOne = ActiveDesignFile.Views(1)
  Dim vwTwo As view
  Set vwTwo = ActiveDesignFile.Views(2)
  vwTwo.Rotation = Matrix3dIdentity
  On Error Resume Next
  vwTwo.Fit True
  On Error GoTo 0
  ' Adjust extents and origin for 3D
  Dim pntExtents As Point3d
  pntExtents = vwOne.Extents
  pntExtents.Z = vwTwo.Extents.Z
  Dim pntOrigin As Point3d
  pntOrigin = vwOne.Origin
  pntOrigin.Z = vwTwo.Origin.Z
  vwTwo.SetArea pntOrigin, pntExtents, vwOne.Rotation, vwOne.ActiveDepth
  ' Get the average element elevation in the view and set the center to that
  Dim dblAvgElev As Double
  dblAvgElev = GetViewElementsAverageElevation(vwTwo)
  ' Rotate up 60 degrees about the X axis
  vwTwo.Rotation = Matrix3dFromAxisAndRotationAngle(0, -1 * Pi / 3)
  vwTwo.Center = Point3dFromXYZ(vwOne.Center.X, vwOne.Center.Y, dblAvgElev)
  
  vwTwo.ClipVolume = True
  vwTwo.ClipFront = False
  vwTwo.ClipBack = False
  
  vwTwo.Redraw
  ActiveDesignFile.Views(2).Select

  ' Make View 1 active
  ActiveDesignFile.Views(1).Select
  CadInputQueue.SendCommand "UPDATE VIEW EXTENDED 1"
  ' CadInputQueue.SendCommand "FILEDESIGN"
  CadInputQueue.SendCommand "CHOOSE NONE"

End Sub

Sub TwoView3DF9()

  ActiveDesignFile.Views(1).IsOpen = True
  ActiveDesignFile.Views(2).IsOpen = True

  ' Close the rest
  Dim i As Integer
  For i = 3 To 8
    ActiveDesignFile.Views(i).IsOpen = False
  Next i

  ' Panel the views (maximize first so TILE will make them side-by-side)
  ActiveDesignFile.Views(2).Maximize
  ActiveDesignFile.Views(1).Maximize
  CadInputQueue.SendKeyin "view set model ""Default"" 1"
  CadInputQueue.SendCommand "WINDOW TILE"
  
  
  ' Try to find the 3D model for the active model
  Dim strModName3D As String
  strModName3D = ActiveModelReference.name & "-3D"
  Dim blnFound As Boolean
  blnFound = False
  Dim modRefCurr As ModelReference
  For Each modRefCurr In ActiveDesignFile.Models
    If UCase(modRefCurr.name) = UCase(strModName3D) Then
      ' Found it
      blnFound = True
      CadInputQueue.SendKeyin "view set model """ & modRefCurr.name & """ 2"
      CadInputQueue.SendCommand "WINDOW TILE"
      ' Stop looking
      Exit For
    End If
  Next modRefCurr
  If Not blnFound Then
    ' Didn't find the standard one so set view 2 to the first "*-3D" model found
    For Each modRefCurr In ActiveDesignFile.Models
      If UCase(Right(modRefCurr.name, 3)) = "-3D" Then
        ' Found one so use it
        blnFound = True
        CadInputQueue.SendKeyin "view set model """ & modRefCurr.name & """ 2"
        CadInputQueue.SendCommand "WINDOW TILE"
        ' Stop looking
        Exit For
      End If
    Next modRefCurr
  End If
  If Not blnFound Then
    ' Didn't find a model with "-3D" at the end so set view 2 to the first 3D model found
    For Each modRefCurr In ActiveDesignFile.Models
      If modRefCurr.Is3D Then
        ' Found one so use it
        blnFound = True
        CadInputQueue.SendKeyin "view set model """ & modRefCurr.name & """ 2"
        CadInputQueue.SendCommand "WINDOW TILE"
        ' Stop looking
        Exit For
      End If
    Next modRefCurr
  End If

  ' Set view 2 to illustration -ignore lighting
  CadInputQueue.SendKeyin "CHANGE VIEW CUSTOM ""Illustration:Ignore Lighting"" 2"
  CadInputQueue.SendKeyin "MDL KEYIN BENTLEY.VIEWATTRIBUTESDIALOG,VAD VIEWATTRIBUTESDIALOG SETATTRIBUTE 2 ClipVolume False "

  ' Set view 2 to the same range as view 1
  Dim vwOne As view
  Set vwOne = ActiveDesignFile.Views(1)
  Dim vwTwo As view
  Set vwTwo = ActiveDesignFile.Views(2)
  vwTwo.Rotation = Matrix3dIdentity
  On Error Resume Next
  vwTwo.Fit True
  On Error GoTo 0
  ' Adjust extents and origin for 3D
  Dim pntExtents As Point3d
  pntExtents = vwOne.Extents
  pntExtents.Z = vwTwo.Extents.Z
  Dim pntOrigin As Point3d
  pntOrigin = vwOne.Origin
  pntOrigin.Z = vwTwo.Origin.Z
  vwTwo.SetArea pntOrigin, pntExtents, vwOne.Rotation, vwOne.ActiveDepth
  ' Get the average element elevation in the view and set the center to that
  Dim dblAvgElev As Double
  dblAvgElev = GetViewElementsAverageElevation(vwTwo)
  ' Rotate up 60 degrees about the X axis
  vwTwo.Rotation = Matrix3dFromAxisAndRotationAngle(0, -1 * Pi / 3)
  vwTwo.Center = Point3dFromXYZ(vwOne.Center.X, vwOne.Center.Y, dblAvgElev)
  
  vwTwo.ClipVolume = True
  vwTwo.ClipFront = False
  vwTwo.ClipBack = False
  
  vwTwo.Redraw
  ActiveDesignFile.Views(2).Select

  ' Make View 1 active
  ActiveDesignFile.Views(1).Select
  CadInputQueue.SendCommand "UPDATE VIEW EXTENDED 1"
  ' CadInputQueue.SendCommand "FILEDESIGN"
  CadInputQueue.SendCommand "CHOOSE NONE"

End Sub


Function GetViewElementsAverageElevation(View3D As view) As Double

  ' Get a fence from the view
  Dim pts(1 To 4) As Point2d
  Dim size As Point3d
  size = View3D.Extents
  pts(2).Y = size.Y
  pts(3).X = size.X
  pts(3).Y = size.Y
  pts(4).X = size.X
  ActiveDesignFile.Fence.DefineFromViewPoints View3D, pts

  ' Get the elements in the fence (inside)
  Dim elmEnum As ElementEnumerator
  ActiveSettings.FenceClip = False
  ActiveSettings.FenceOverlap = True
  ActiveSettings.FenceVoid = False
  Set elmEnum = ActiveDesignFile.Fence.GetContents
  Dim lngElmCnt As Long
  Dim dblElmElevSum As Double
  Do While elmEnum.MoveNext
    lngElmCnt = lngElmCnt + 1
    Dim dblElmElevAvg As Double
    dblElmElevAvg = (elmEnum.Current.Range.Low.Z + elmEnum.Current.Range.High.Z) / 2
    dblElmElevSum = dblElmElevSum + dblElmElevAvg
  Loop
  
  If lngElmCnt > 0 Then
    ' Compute the average
    GetViewElementsAverageElevation = dblElmElevSum / lngElmCnt
  Else
    ' No elements so use the view center
    GetViewElementsAverageElevation = View3D.Center.Z
  End If

End Function

Sub ToggleViewConstructions()

  ' Toggle constructions in current view
  Dim i As Integer
  For i = 1 To 8
    If ActiveDesignFile.Views.Item(i).IsSelected Then
      ' Toggle this one and quit looking
      ActiveDesignFile.Views.Item(i).DisplaysConstructions = Not ActiveDesignFile.Views.Item(i).DisplaysConstructions
      ActiveDesignFile.Views.Item(i).Redraw
      Exit For
    End If
  Next i
  'CursorInformation.CurrentView.DisplaysConstructions = Not CursorInformation.CurrentView.DisplaysConstructions
  'CursorInformation.CurrentView.Redraw

End Sub

Sub DeleteUnusedFonts()

    Dim startPoint As Point3d
    Dim point As Point3d, point2 As Point3d
    Dim lngTemp As Long
'   Send a keyin that can be a command string
    CadInputQueue.SendKeyin "delete unused fonts"
'   Start a command
    CadInputQueue.SendCommand "FILEDESIGN"
    CadInputQueue.SendCommand "COMPRESS DESIGN CONFIRM"

End Sub

Sub SetActiveModelToDrawLast()

  ' Shift attachments
  Dim i As Long
  For i = ActiveModelReference.Attachments.Count To 1 Step -1
    ActiveModelReference.Attachments(i).UpdateOrder = 0
  Next i

  ' Set the color adjustment factor
  If ActiveModelReference.Attachments.Count > 0 Then
    ' Get the first attachment to compare
    Dim attCurr As Attachment
    Set attCurr = ActiveModelReference.Attachments(1)

    ' Compose the C expression to access the referenceFile C struct
'    Dim lngModRefP As Variant
'    lngModRefP = attCurr.MdlModelRefP
'    Dim lngRefStruct As LongPtr
'    lngRefStruct = mdlRefFile_getInfo(lngModRefP)
'    Dim refName As String
'    refName = "((struct referenceFile *)" & lngRefStruct & ")"
''    refName = "((struct referenceFile *)" & lngModRefP & ")"
'
'    Dim lngValueAdj As Long
'    Dim lngSaturAdj As Long
'
'    ' Get the current values
'    lngValueAdj = GetCExpressionValue(refName & "->display.hsvValueAdjustment")
'    lngSaturAdj = GetCExpressionValue(refName & "->display.hsvSaturationAdjustment")
'
'    ' Toggle the color adjustment factor for all references
'    If lngValueAdj = 0 And lngSaturAdj = 0 Then
'      CadInputQueue.SendKeyin "reference adjustcolors 30,50 *"
'    Else
'      CadInputQueue.SendKeyin "reference adjustcolors 100,100 *"
'    End If
'    CadInputQueue.SendCommand "FILEDESIGN"
    ' Toggle the color adjustment factor for all references
    If Not attCurr.PrintColorAdjustment Then
      CadInputQueue.SendKeyin "reference adjustcolors 30,50 *"
      attCurr.PrintColorAdjustment = True
    Else
      CadInputQueue.SendKeyin "reference adjustcolors 100,100 *"
      attCurr.PrintColorAdjustment = False
    End If
    CadInputQueue.SendCommand "FILEDESIGN"
  End If

End Sub

Sub AnalyzeTerrainModelPoint()

    Dim startPoint As Point3d
    Dim point As Point3d, point2 As Point3d
    Dim lngTemp As Long

'   Start a command
    CadInputQueue.SendCommand "DMSG ACTIVATETOOLBYPATH Civil AccuDraw\Toggle Civil AccuDraw"

    CadInputQueue.SendCommand "CIVILCOORD ACTIVATE "

    CadInputQueue.SendCommand "DMSG ACTIVATETOOLBYPATH Civil AccuDraw\Station-Offset"

    CadInputQueue.SendCommand "TERRAINMODEL ANALYZE POINT"

End Sub

Sub ExaggerateZForAttachment()

  ' Make sure the model doesn't already exist
  Dim modCurr As ModelReference
  For Each modCurr In ActiveDesignFile.Models
    If modCurr.name = "3D Temporary Visualization" Then
      ' Found one so remove it
      ActiveDesignFile.Models.Delete modCurr
      Exit For
    End If
  Next modCurr

'  Dim intViewNum As Integer
'  intViewNum = CursorInformation.CurrentView.Index

  ' Save the original model to return to when dialog is closed
  Set frmExaggerateZ.OriginalModel = ActiveModelReference

  ' Create new model
  Dim modRefTemp As ModelReference
  Set modRefTemp = ActiveDesignFile.Models.Add(ActiveModelReference, "3D Temporary Visualization", "Temporary model for visualizing exaggerated verticals", msdModelTypeNormal, True)

  ' Switch to model and attach the current model as a reference
  Dim strInitialModel As String
  strInitialModel = ActiveModelReference.name
  modRefTemp.Activate
  Dim attTemp As Attachment
  Set attTemp = modRefTemp.Attachments.Add(ActiveDesignFile.FullName, strInitialModel, "Temp3DVis", "3D Temporary Visualization", Point3dZero, Point3dZero)

  ' Fit the first view
  On Error Resume Next
  Dim i As Integer
  For i = 1 To 8
    If ActiveDesignFile.Views(i).IsOpen Then
    If ActiveDesignFile.Views(i).IsSelected Then
      ActiveDesignFile.Views(i).Maximize
      ActiveDesignFile.Views(i).Fit True
      ActiveDesignFile.Views(i).Redraw
    Else
      ActiveDesignFile.Views(i).IsOpen = False
    End If
    End If
  Next i
  On Error GoTo 0
'  CursorInformation.CurrentView.Fit True
'  CursorInformation.CurrentView.Redraw
'  ActiveDesignFile.Views(intViewNum).Fit True
'  ActiveDesignFile.Views(intViewNum).Redraw

  ' Disclaimer
  MsgBox "Note: Visual Inspection Aid Only.  Elevation Values Will Be Shifted.", vbInformation, "Exaggerate Z For Attachment"

  ' Set the temporary model to remove when dialog is closed
  Set frmExaggerateZ.TempModel = modRefTemp

  ' Show the dialog
  frmExaggerateZ.Show

End Sub

Sub ThreeViewsPLPROF3D()
  
  ' Close views 2-8
  Dim i As Integer
  For i = 2 To 8
    ActiveDesignFile.Views(i).IsOpen = False
  Next i
  
  ' Open Views 1,3, and 4.  1 = Plan, 3 = 3D Model, 4 = Profile
  ActiveDesignFile.Views(1).IsOpen = True
  CadInputQueue.SendKeyin "view set model ""Default"" 1"
  ActiveDesignFile.Views(1).Maximize
  ActiveDesignFile.Views(3).IsOpen = True
  ActiveDesignFile.Views(4).IsOpen = True
  CadInputQueue.SendKeyin "MDL KEYIN BENTLEY.VIEWATTRIBUTESDIALOG,VAD VIEWATTRIBUTESDIALOG SETATTRIBUTE 3 Grid True"
   
  ' Take advantage of the seed file view arrangements in the Civil Workset to position views in a logical manner
  CadInputQueue.SendKeyin "WINDOW ARRANGE "
  
  ' Try to find the 3D model for the active model and assign to View 3
  Dim strModName3D As String
  strModName3D = ActiveModelReference.name & "-3D"
  Dim blnFound As Boolean
  blnFound = False
  Dim modRefCurr As ModelReference
  For Each modRefCurr In ActiveDesignFile.Models
    If UCase(modRefCurr.name) = UCase(strModName3D) Then
      ' Found it
      blnFound = True
      CadInputQueue.SendKeyin "view set model """ & modRefCurr.name & """ 3"
    ' Stop looking
      Exit For
    End If
  Next modRefCurr
  If Not blnFound Then
    ' Didn't find the standard one so set view 3 to the first "*-3D" model found
    For Each modRefCurr In ActiveDesignFile.Models
      If UCase(Right(modRefCurr.name, 3)) = "-3D" Then
        ' Found one so use it
        blnFound = True
        CadInputQueue.SendKeyin "view set model """ & modRefCurr.name & """ 3"
      ' Stop looking
        Exit For
      End If
    Next modRefCurr
  End If
  If Not blnFound Then
    ' Didn't find a model with "-3D" at the end so set view 3 to the first 3D model found
    For Each modRefCurr In ActiveDesignFile.Models
      If modRefCurr.Is3D Then
        ' Found one so use it
        blnFound = True
        CadInputQueue.SendKeyin "view set model """ & modRefCurr.name & """ 3"
      ' Stop looking
        Exit For
      End If
    Next modRefCurr
  End If

  ' Set view 3 to Smooth
  ' CadInputQueue.SendKeyin "CHANGE VIEW CUSTOM ""Smooth"" 3"
  CadInputQueue.SendKeyin "CHANGE VIEW CUSTOM ""Illustration:Ignore Lighting"" 3"
  CadInputQueue.SendKeyin "MDL KEYIN BENTLEY.VIEWATTRIBUTESDIALOG,VAD VIEWATTRIBUTESDIALOG SETATTRIBUTE 3 ClipVolume False "

  ' Set view 3 to the same range as view 1
  Dim vwOne As view
  Set vwOne = ActiveDesignFile.Views(1)
  Dim vwTwo As view
  Set vwTwo = ActiveDesignFile.Views(3)
  vwTwo.Rotation = Matrix3dIdentity
  On Error Resume Next
  vwTwo.Fit True
  On Error GoTo 0
  ' Adjust extents and origin for 3D
  Dim pntExtents As Point3d
  pntExtents = vwOne.Extents
  pntExtents.Z = vwTwo.Extents.Z
  Dim pntOrigin As Point3d
  pntOrigin = vwOne.Origin
  pntOrigin.Z = vwTwo.Origin.Z
  vwTwo.SetArea pntOrigin, pntExtents, vwOne.Rotation, vwOne.ActiveDepth
  ' Get the average element elevation in the view and set the center to that
  Dim dblAvgElev As Double
  dblAvgElev = GetViewElementsAverageElevation(vwTwo)
  ' Rotate up 60 degrees about the X axis
  vwTwo.Rotation = Matrix3dFromAxisAndRotationAngle(0, -1 * Pi / 3)
  vwTwo.Center = Point3dFromXYZ(vwOne.Center.X, vwOne.Center.Y, dblAvgElev)
  
  vwTwo.ClipVolume = True
  vwTwo.ClipFront = False
  vwTwo.ClipBack = False
  
  vwTwo.Redraw
  ActiveDesignFile.Views(3).Select

  ' Make View 1 active
  ActiveDesignFile.Views(1).Select
  CadInputQueue.SendCommand "UPDATE VIEW EXTENDED 1"
  ' CadInputQueue.SendCommand "FILEDESIGN"
  CadInputQueue.SendCommand "CHOOSE NONE"
  
  'Execute the Open Profile Model Command
  Dim dlgResult As VbMsgBoxResult
  dlgResult = MsgBox("Select OK to Create a Dynamic Profile View", vbOKCancel, "Open a Dynamic Profile View")
  If dlgResult = 1 Then
    Call OpenProfileModel
  End If

End Sub

Sub ThreeViewsPLXS3D()
  
  ' Close views 2-8
  Dim i As Integer
  For i = 2 To 8
    ActiveDesignFile.Views(i).IsOpen = False
  Next i
  
  ' Open Views 1,3, and 7.  1 = Plan, 3 = 3D Model, 7 = XS
  ActiveDesignFile.Views(1).IsOpen = True
  CadInputQueue.SendKeyin "view set model ""Default"" 1"
  ActiveDesignFile.Views(1).Maximize
  ActiveDesignFile.Views(3).IsOpen = True
  ActiveDesignFile.Views(7).IsOpen = True
  CadInputQueue.SendKeyin "MDL KEYIN BENTLEY.VIEWATTRIBUTESDIALOG,VAD VIEWATTRIBUTESDIALOG SETATTRIBUTE 6 Grid True"
   
  ' Take advantage of the seed file view arrangements in the Civil Workset to position views in a logical manner
  CadInputQueue.SendKeyin "WINDOW ARRANGE "
  
  ' Try to find the 3D model for the active model and assign to View 3
  Dim strModName3D As String
  strModName3D = ActiveModelReference.name & "-3D"
  Dim blnFound As Boolean
  blnFound = False
  Dim modRefCurr As ModelReference
  For Each modRefCurr In ActiveDesignFile.Models
    If UCase(modRefCurr.name) = UCase(strModName3D) Then
      ' Found it
      blnFound = True
      CadInputQueue.SendKeyin "view set model """ & modRefCurr.name & """ 3"
    ' Stop looking
      Exit For
    End If
  Next modRefCurr
  If Not blnFound Then
    ' Didn't find the standard one so set view 3 to the first "*-3D" model found
    For Each modRefCurr In ActiveDesignFile.Models
      If UCase(Right(modRefCurr.name, 3)) = "-3D" Then
        ' Found one so use it
        blnFound = True
        CadInputQueue.SendKeyin "view set model """ & modRefCurr.name & """ 3"
      ' Stop looking
        Exit For
      End If
    Next modRefCurr
  End If
  If Not blnFound Then
    ' Didn't find a model with "-3D" at the end so set view 3 to the first 3D model found
    For Each modRefCurr In ActiveDesignFile.Models
      If modRefCurr.Is3D Then
        ' Found one so use it
        blnFound = True
        CadInputQueue.SendKeyin "view set model """ & modRefCurr.name & """ 3"
      ' Stop looking
        Exit For
      End If
    Next modRefCurr
  End If

  ' Set view 3 to Smooth
  ' CadInputQueue.SendKeyin "CHANGE VIEW CUSTOM ""Smooth"" 3"
  CadInputQueue.SendKeyin "CHANGE VIEW CUSTOM ""Illustration:Ignore Lighting"" 3"
  CadInputQueue.SendKeyin "MDL KEYIN BENTLEY.VIEWATTRIBUTESDIALOG,VAD VIEWATTRIBUTESDIALOG SETATTRIBUTE 3 ClipVolume False "

  ' Set view 3 to the same range as view 1
  Dim vwOne As view
  Set vwOne = ActiveDesignFile.Views(1)
  Dim vwTwo As view
  Set vwTwo = ActiveDesignFile.Views(3)
  vwTwo.Rotation = Matrix3dIdentity
  On Error Resume Next
  vwTwo.Fit True
  On Error GoTo 0
  ' Adjust extents and origin for 3D
  Dim pntExtents As Point3d
  pntExtents = vwOne.Extents
  pntExtents.Z = vwTwo.Extents.Z
  Dim pntOrigin As Point3d
  pntOrigin = vwOne.Origin
  pntOrigin.Z = vwTwo.Origin.Z
  vwTwo.SetArea pntOrigin, pntExtents, vwOne.Rotation, vwOne.ActiveDepth
  ' Get the average element elevation in the view and set the center to that
  Dim dblAvgElev As Double
  dblAvgElev = GetViewElementsAverageElevation(vwTwo)
  ' Rotate up 60 degrees about the X axis
  vwTwo.Rotation = Matrix3dFromAxisAndRotationAngle(0, -1 * Pi / 3)
  vwTwo.Center = Point3dFromXYZ(vwOne.Center.X, vwOne.Center.Y, dblAvgElev)
  
  vwTwo.ClipVolume = True
  vwTwo.ClipFront = False
  vwTwo.ClipBack = False
  
  vwTwo.Redraw
  ActiveDesignFile.Views(3).Select

  ' Make View 1 active
  ActiveDesignFile.Views(1).Select
  CadInputQueue.SendCommand "UPDATE VIEW EXTENDED 1"
  ' CadInputQueue.SendCommand "FILEDESIGN"
  CadInputQueue.SendCommand "CHOOSE NONE"
  
    
  'Execute the Open DynamicXS Model Command
   Dim dlgResult As VbMsgBoxResult
   dlgResult = MsgBox("Select OK to Create a Dynamic XS View", vbOKCancel, "Open a Dynamic Cross Section View")
   If dlgResult = 1 Then
     Call OpenDynamicXSModel
   End If
    
End Sub

Sub TwoViewsPLPROF()
  
  ' Close views 2-8
  Dim i As Integer
  For i = 2 To 8
    ActiveDesignFile.Views(i).IsOpen = False
  Next i
  
  ' Open Views 1 and 4.  1 = Plan, 4 = Profile
  ActiveDesignFile.Views(1).IsOpen = True
  CadInputQueue.SendKeyin "view set model ""Default"" 1"
  ActiveDesignFile.Views(1).Maximize
  ActiveDesignFile.Views(4).IsOpen = True
  CadInputQueue.SendKeyin "MDL KEYIN BENTLEY.VIEWATTRIBUTESDIALOG,VAD VIEWATTRIBUTESDIALOG SETATTRIBUTE 3 Grid True"
   
  ' Take advantage of the seed file view arrangements in the Civil Workset to position views in a logical manner
  CadInputQueue.SendKeyin "WINDOW ARRANGE "
  
  
  ' Make View 1 active
  ActiveDesignFile.Views(1).Select
  CadInputQueue.SendCommand "UPDATE VIEW EXTENDED 1"
  ' CadInputQueue.SendCommand "FILEDESIGN"
  CadInputQueue.SendCommand "CHOOSE NONE"
  
  'Execute the Open Profile Model Command
  Dim dlgResult As VbMsgBoxResult
  dlgResult = MsgBox("Select OK to Create a Dynamic Profile View", vbOKCancel, "Open a Dynamic Profile View")
  If dlgResult = 1 Then
    Call OpenProfileModel
  End If

End Sub

Sub OpenProfileModel()

  CadInputQueue.SendCommand "GEOMETRY PROFILE OPEN VIEW"
  
  Dim intPointsIssued As Integer
  intPointsIssued = 0

  Dim pntPrev As Point3d
  pntPrev = CommandState.LastDataPoint
  Dim pntCurr As Point3d

  Dim timeNow As Date
  Dim timeStart As Date
  timeStart = Now
  
  Dim dblTimeElapsed As Double
  dblTimeElapsed = Now() - timeStart
  
  ' Wait for two data points or 30 seconds, which ever comes first
  Do While intPointsIssued < 2 And dblTimeElapsed < 30
    ' Wait two seconds, allowing other processes to run
    timeNow = Now()
    Do While DateDiff("s", timeNow, Now()) < 2
      DoEvents
    Loop
    
    ' Get the last data point issued
    pntCurr = CommandState.LastDataPoint
    If Not Point3dEqual(pntCurr, pntPrev) Then
      ' Point changed
      intPointsIssued = intPointsIssued + 1
      pntPrev = pntCurr
    End If
    
    ' Get the change in time
    dblTimeElapsed = DateDiff("s", timeStart, Now())
  Loop
  
  If intPointsIssued <= 2 And dblTimeElapsed < 30 Then
  ' Wait two seconds, allowing other processes to run
    timeNow = Now()
    Do While DateDiff("s", timeNow, Now()) < 1
      DoEvents
    Loop
    CadInputQueue.SendCommand "CHOOSE NONE"
  
  Else
      CadInputQueue.SendCommand "CHOOSE NONE"
  End If

End Sub

Sub OpenDynamicXSModel()

  CadInputQueue.SendCommand "GEOMETRY CROSSSECTION OPEN VIEW"
  
End Sub

Attribute VB_Name = "frmExaggerateZ"
Attribute VB_Base = "0{B8D7911A-A8D9-4B34-94A0-D5A45D0F0EBE}{C2A0941C-69CA-489F-BBE4-9DD9A0417CC9}"
Attribute VB_GlobalNameSpace = False
Attribute VB_Creatable = False
Attribute VB_PredeclaredId = True
Attribute VB_Exposed = False
Attribute VB_TemplateDerived = False
Attribute VB_Customizable = False

Public OriginalModel As ModelReference
Public TempModel As ModelReference

Private Sub UserForm_Activate()

  ' Set default exaggeration
  txtExaggeration.Text = "1"

End Sub

Private Sub UserForm_Terminate()

  ' Try to activate the original model
  If Not OriginalModel Is Nothing Then
    OriginalModel.Activate
  End If

  ' Try to remove the temporary model
  If Not TempModel Is Nothing Then
    If Not TempModel.IsActive Then
      ActiveDesignFile.Models.Delete TempModel
    End If
  End If

End Sub

Private Sub cmdExaggerate_Click()

  If Not TempModel Is Nothing And txtExaggeration.Text <> "" Then
    Dim dblExaggeration As Double
    On Error Resume Next
    dblExaggeration = txtExaggeration.Text
    On Error GoTo 0
    If dblExaggeration <= 0 Then
      MsgBox "Invalid Exaggeration value"
      Exit Sub
    End If
    
    If ActiveModelReference.Attachments.Count > 0 Then
      If ActiveModelReference.Attachments(1).LogicalName = "Temp3DVis" Then
        ' Good attachment so use it
        Dim GetDP As New GetDPLocation
        GetDP.ZScale = dblExaggeration
        GetDP.AttInx = 1
        CommandState.EnableAccuSnap
        CommandState.StartPrimitive GetDP
      Else
        ' Bad attachment
        MsgBox ("Could not obtain attachment")
        Exit Sub
      End If
    Else
      ' Bad attachment
      MsgBox ("Could not obtain attachment")
      Exit Sub
    End If
  Else
    ' Bad attachment
    MsgBox ("Please select an attachment")
    Exit Sub
  End If

End Sub

Private Sub cmdRemoveExaggeration_Click()

  If ActiveModelReference.Attachments.Count > 0 Then
    If ActiveModelReference.Attachments(1).LogicalName = "Temp3DVis" Then
      ' Good attachment so use it
      Dim trnsCurr As Transform3d
      trnsCurr = ActiveModelReference.Attachments(1).GetMasterToReferenceTransform
      ActiveModelReference.Attachments(1).Transform trnsCurr, True
      ActiveModelReference.Attachments(1).Rewrite
      CursorInformation.CurrentView.Redraw
    Else
      ' Bad attachment
      MsgBox ("Could not obtain attachment")
      Exit Sub
    End If
  Else
    ' Bad attachment
    MsgBox ("Could not obtain attachment")
    Exit Sub
  End If

End Sub
