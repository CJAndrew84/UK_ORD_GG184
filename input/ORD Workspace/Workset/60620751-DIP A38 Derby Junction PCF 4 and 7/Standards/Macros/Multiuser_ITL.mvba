Attribute VB_Name = "Open_Template_Editor"
' Macro for multi-user itl template library use - Created by Mark Shamoun (Arcadis NSW)
' -----------------------------------------------------------------------------------------------

Declare PtrSafe Function WNetGetUser Lib "mpr.dll" Alias "WNetGetUserA" (ByVal lpName As String, ByVal lpUserName As String, lpnLength As Long) As Long
Sub MultiUserITL()

Const CfgVarName As String = "CIVIL_ROADWAY_TEMPLATE_LIBRARY"

Dim cfgVarValue As String, LocUser As String, GetFileOwner As String
Dim Currvalue As String, Newvalue As String, itlPath As String


' Get current variable for itl location
Currvalue = ActiveWorkspace.ConfigurationVariableValue(CfgVarName)


' Run normally if itl located on local drive (ie. C or D) - disable if using sync software
If FileExists(Currvalue) And Not (Left(Currvalue, 1) = "C") And Not (Left(Currvalue, 1) = "D") Then

    ' Get current windows username
        ' Buffer size for the return string.
    Const lpnLength As Integer = 255
        ' Get return buffer space.
    Dim status As Integer
        ' For getting user information.
    Dim lpName, lpUserName As String
        ' Assign the buffer size constant to lpUserName.
    lpUserName = Space$(lpnLength + 1)
        ' Get the log-on name of the person using product.
    status = WNetGetUser(lpName, lpUserName, lpnLength)
    lpUserName = Left$(lpUserName, InStr(lpUserName, Chr(0)) - 1)


    ' Check if loc file exists and if created by current user delete loc file.
    If FileExists(Currvalue + ".loc") Then
        Open Currvalue + ".loc" For Input As #1
        Do Until EOF(1)
            Line Input #1, LocUser
        Loop
        Close #1
        
        ' Check if current user created loc file
        If LocUser = Chr(34) + lpUserName + Chr(34) Then
        ' if so, delete temp loc file
        Kill Currvalue + ".loc"
        End If
    End If

    
    If LocUser = "" Then
        LocUser = "unknown"
    End If

    
    ' Check if loc file exists and display error if itl is in use
    If FileExists(Currvalue + ".loc") Then
    
        '' Get Loc file owner
        'Dim obj As Object
        'Dim fso As Object
        'Set fso = CreateObject("Scripting.FileSystemObject")
        'Set obj = CreateObject("Shell.Application")
        'With obj.Namespace(fso.GetParentFolderName(Currvalue + ".loc"))
        '   'return extended file property 9 of file indexed by name
        '   getfileAuthor = .GetDetailsOf(.Items.Item(fso.GetFileName(Currvalue + ".loc")), 10)
        'End With
    
        CadInputQueue.SendCommand "beep"
        ShowMessage "ITL file: " + Chr(34) + Currvalue + Chr(34) + " in use by User: " + LocUser
        ShowMessage "ERROR - Template Library is currently being edited by " + LocUser + ". Try again later.", , msdMessageCenterPriorityError
        MsgBox "ERROR - Template Library is currently being edited by " + LocUser + ". Try again later. See Message Center for more info."
        Exit Sub
    End If


    ' Create loc file to indicate itl is in use & write username
    Open Currvalue + ".loc" For Output As #2
    Write #2, lpUserName
    Close #2

    
    ' Backup current itl
    If FileExists(Currvalue + ".bak") Then
        If FileExists(Currvalue + ".bak1") Then
            FileCopy Currvalue + ".bak1", Currvalue + ".bak2"
            FileCopy Currvalue + ".bak", Currvalue + ".bak1"
            FileCopy Currvalue, Currvalue + ".bak"
        Else
            FileCopy Currvalue + ".bak", Currvalue + ".bak1"
            FileCopy Currvalue, Currvalue + ".bak"
        End If
    Else
        FileCopy Currvalue, Currvalue + ".bak"
    End If
    
    
    ' Open itl template library
    CadInputQueue.SendCommand "corridor templatelibrary open"
    
    
    ' Delete temp loc file
    Kill Currvalue + ".loc"
    
    ' Exit Macro
    Exit Sub

Else

' Open itl template library normally with backup

If Not (FileExists(Currvalue)) Then
    CadInputQueue.SendCommand "beep"
    ShowMessage "ERROR - " + Currvalue + " not found", , msdMessageCenterPriorityError
End If

' Backup current itl
If FileExists(Currvalue + ".bak") Then
    If FileExists(Currvalue + ".bak1") Then
        FileCopy Currvalue + ".bak1", Currvalue + ".bak2"
        FileCopy Currvalue + ".bak", Currvalue + ".bak1"
        FileCopy Currvalue, Currvalue + ".bak"
    Else
        FileCopy Currvalue + ".bak", Currvalue + ".bak1"
        FileCopy Currvalue, Currvalue + ".bak"
    End If
Else
    FileCopy Currvalue, Currvalue + ".bak"
End If
    
CadInputQueue.SendCommand "corridor templatelibrary open"


End If

CadInputQueue.SendCommand "powerselector single"

End Sub

Function FileExists(ByVal strFile As String, Optional bFindFolders As Boolean) As Boolean
    'Purpose:   Return True if the file exists, even if it is hidden.
    'Arguments: strFile: File name to look for. Current directory searched if no path included.
    '           bFindFolders. If strFile is a folder, FileExists() returns False unless this argument is True.
    'Note:      Does not look inside subdirectories for the file.
    'Author:    Allen Browne. http://allenbrowne.com June, 2006.
    Dim lngAttributes As Long

    'Include read-only files, hidden files, system files.
    lngAttributes = (vbReadOnly Or vbHidden Or vbSystem)

    If bFindFolders Then
        lngAttributes = (lngAttributes Or vbDirectory) 'Include folders as well.
    Else
        'Strip any trailing slash, so Dir does not look inside the folder.
        Do While Right$(strFile, 1) = "\"
            strFile = Left$(strFile, Len(strFile) - 1)
        Loop
    End If

    'If Dir() returns something, the file exists.
    On Error Resume Next
    FileExists = (Len(Dir(strFile, lngAttributes)) > 0)
End Function
