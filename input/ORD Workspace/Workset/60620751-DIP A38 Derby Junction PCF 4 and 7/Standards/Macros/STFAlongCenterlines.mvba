Attribute VB_Name = "Main"
Const LEVELCOL = 1
Const FAMILYCOL = 2
Const PARTCOL = 3
Const SECTIONCOL = 4
Const GRADECOL = 5
Const MARKCOL = 6
Const PPCOL = 7
Const TYPECOL = 8
Const MATERIALCOL = 9
Const STATUSCOL = 10
Const CLASSCOL = 11
Const USER1COL = 12
Const USER2COL = 13
Const USER3COL = 14
Const USER4COL = 15

' Declare necessary API routines:
Declare Function FindWindow Lib "user32" Alias _
                 "FindWindowA" (ByVal lpClassName As String, _
                                ByVal lpWindowName As Long) As Long

Declare Function SendMessage Lib "user32" Alias _
                 "SendMessageA" (ByVal hWnd As Long, ByVal wMsg As Long, _
                                 ByVal wParam As Long, _
                                 ByVal lParam As Long) As Long

Sub DetectExcel()
    ' Procedure dectects a running Excel and registers it.
    Const WM_USER = 1024
    Dim hWnd As Long
    
    ' If Excel is running this API call returns its handle.
    hWnd = FindWindow("XLMAIN", 0)
    If hWnd = 0 Then    ' 0 means Excel not running.
        Exit Sub
    Else
    
    ' Excel is running so use the SendMessage API
    ' function to enter it in the Running Object Table.
        SendMessage hWnd, WM_USER + 18, 0, 0
    End If
End Sub


Sub Main()
    Dim oXLWSheet As Excel.Worksheet

    Dim cell As Range
    Dim area As Range
    Dim row As Range
    Dim rowNumber As Integer
    Dim sectionName As String
    Dim familyName As String
    Dim levelName As String
    Dim partName As String
    Dim gradeName As String
    Dim markName As String
    Dim memTypeName As String
    Dim materialName As String
    Dim statusName As String
    Dim className As String
    Dim user1Name As String
    Dim user2Name As String
    Dim user3Name As String
    Dim user4Name As String
    Dim PP As Integer
    Dim oScanCriteria As ElementScanCriteria
    Dim oLevel As Level
    Dim oElement As Element
    Dim startpnt As Point3d
    Dim endpnt As Point3d
    
    Dim MyXL As Object                  ' Variable to hold reference to Microsoft Excel.
    Dim ExcelWasNotRunning As Boolean   ' Flag for final release.

    ' Test to see if there is a copy of Microsoft Excel already running.
    On Error Resume Next    ' Defer error trapping.
   
    ' Getobject function called without the first argument returns a
    ' reference to an instance of the application. If the application isn't
    ' running, an error occurs.
    Set MyXL = GetObject(, "Excel.Application")
    If Err.Number <> 0 Then
        ExcelWasNotRunning = True
    End If
    
    Err.Clear    ' Clear Err object in case error occurred.
    ' Check for Microsoft Excel. If Microsoft Excel is running,
    ' enter it into the Running Object table.
    DetectExcel
    
    Set oXLWSheet = MyXL.ActiveWorkbook.ActiveSheet 'save open excel file as a local var oXLWSheet
    Set area = MyXL.ActiveWorkbook.Worksheets("Detailed Members").Range("2:100")
    rowNumber = 1
    For Each row In area.Rows
        Set cell = row.Cells
        Set oScanCriteria = New ElementScanCriteria
        
        ' set the cell RANGE to include all the selectd cells on the current row
'        rowNumber = cell.row
      
        levelName = cell.Cells(0, LEVELCOL).Value2
        Set oLevel = ActiveDesignFile.Levels.Find(levelName)
        If oLevel Is Nothing Then
        
        Else
            familyName = cell.Cells(0, FAMILYCOL).Value2
            partName = cell.Cells(0, PARTCOL).Value2
            sectionName = cell.Cells(0, SECTIONCOL).Value2
            If Len(sectionName) > 0 Then
                gradeName = cell.Cells(0, GRADECOL).Value2
                markName = cell.Cells(0, MARKCOL).Value2
                PP = cell.Cells(0, PPCOL).Value2
                memTypeName = cell.Cells(0, TYPECOL).Value2
                
                materialName = cell.Cells(0, MATERIALCOL).Value2
                statusName = cell.Cells(0, STATUSCOL).Value2
                className = cell.Cells(0, CLASSCOL).Value2
                user1Name = cell.Cells(0, USER1COL).Value2
                user2Name = cell.Cells(0, USER2COL).Value2
                user3Name = cell.Cells(0, USER3COL).Value2
                user4Name = cell.Cells(0, USER4COL).Value2
       
                Dim member As STFLinearMember
                Set member = New STFLinearMemberList
                Dim section As STFSection
                Set section = New STFSectionList
                
                section.SetName (sectionName)
                member.SetSTFSection section
                
                If Len(familyName) > 0 Then
                    member.SetPartFamily (familyName)
                End If
                
                If Len(partName) > 0 Then
                    member.SetPartName (partName)
                End If
                
                On Error Resume Next
                member.SetMaterial materialName, gradeName
                member.SetMark markName
                member.SetTypeString memTypeName
                member.SetStatus statusName
                member.SetClass className
                member.SetUserString 1, user1Name
                member.SetUserString 2, user2Name
                member.SetUserString 3, user3Name
                member.SetUserString 4, user4Name
                member.SetPlacementPoint PP
                'member.SetRotation 180
                                        
                ' Scan the DGN file for each line, linestring, arc, or curve found on this level
                oScanCriteria.ExcludeAllTypes
                oScanCriteria.IncludeType msdElementTypeLine
                oScanCriteria.IncludeType msdElementTypeLineString
                oScanCriteria.IncludeType msdElementTypeArc
                oScanCriteria.IncludeType msdElementTypeCurve
                oScanCriteria.IncludeType msdElementTypeBsplineCurve
    
                oScanCriteria.ExcludeAllLevels
                Set oLevel = ActiveDesignFile.Levels(levelName)
                oScanCriteria.IncludeLevel oLevel
                Set oEnumerator = ActiveModelReference.Scan(oScanCriteria)
    
                Dim jj As Integer
                Dim path As New TFBrepList

                ' step through the elements
                Do While oEnumerator.MoveNext
                    Set oElement = oEnumerator.Current
                    With oEnumerator.Current
                        If oElement.IsLineElement Then
                            For jj = 1 To oElement.AsLineElement.VerticesCount - 1
                                startpnt = oElement.AsLineElement.Vertex(jj)
                                endpnt = oElement.AsLineElement.Vertex(jj + 1)
                                member.SetPQPoints startpnt, endpnt

                                member.createTFFormRecipeList
                                member.Save True    ' Will create analytical members, too.
                            Next jj
                        Else
                            path.InitFromElement oElement, ActiveModelReference
                            member.SetPath path

                            member.createTFFormRecipeList
                            member.Save True        ' Will create analytical members when supported for curved members.
                        End If
                    End With
                Loop
            End If
        End If
        
        Set oScanCriteria = Nothing
        Set oEnumerator.Current = Nothing
        Set oEnumerator = Nothing
        rowNumber = rowNumber + 1
    Next
    
    Set oXLWBook = Nothing
    Set MyXL = Nothing    ' Release reference to the application and spreadsheet.

End Sub
