Attribute VB_Name = "GetDPLocation"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

' Implement Statement: inform MicroStation that a class is going to provide code for the IPrimitiveCommandEvents interface
Implements IPrimitiveCommandEvents

Public ZScale As Double
Public AttInx As Long

Private Sub IPrimitiveCommandEvents_Cleanup()
  
  ' Clear out the MicroStation prompts
  ShowCommand ""
  ShowPrompt ""

End Sub

Private Sub IPrimitiveCommandEvents_DataPoint(point As Point3d, ByVal view As view)

  Dim mtrxScale As Matrix3d
  Dim mtrxCombined As Matrix3d
  Dim trns As Transform3d
  
  '  Create a scaling matrix
  mtrxScale = Matrix3dFromScaleFactors(1, 1, ZScale)
  
  ' Multiply the matrices to create a matrix that scales and rotates
  mtrxCombined = Matrix3dFromMatrix3dTimesMatrix3d(Matrix3dIdentity, mtrxScale)
  
  '  Create a transform to rotate and scale about a fixed point
  trns = Transform3dFromMatrix3dAndFixedPoint3d(mtrxCombined, point)

  ' Apply the transform to the attachment
  ActiveModelReference.Attachments(AttInx).Transform trns, True
  ActiveModelReference.Attachments(AttInx).Rewrite

  ' Back to default state
  CommandState.StartDefaultCommand
  
  ' Refresh the view
  CursorInformation.CurrentView.Redraw

End Sub

Private Sub IPrimitiveCommandEvents_Dynamics(point As Point3d, ByVal view As view, ByVal DrawMode As MsdDrawingMode)

End Sub

Private Sub IPrimitiveCommandEvents_Keyin(ByVal Keyin As String)

End Sub

Private Sub IPrimitiveCommandEvents_Reset() ' method called when the reset event occurs

  ' Set MicroStation to the default command state
  CommandState.StartDefaultCommand

End Sub

Private Sub IPrimitiveCommandEvents_Start() 'method called at the start of the command
  
  'Provide command and prompt user for required input
  ShowCommand "Exaggerate Z: "

  ShowPrompt "DP Point to scale about"

  ' Turn accusnap on
  CommandState.EnableAccuSnap

End Sub

Attribute VB_Name = "ModViewControl"
Public fsoActive As New FileSystemObject

Declare PtrSafe Function mdlWindow_resize Lib "stdmdlbltin.dll" (ByVal windowP As Long, ByVal cornerNum As Long, ByRef newPositionP As LPoint2d) As Long
Declare PtrSafe Function mdlWindow_viewWindowGet Lib "stdmdlbltin.dll" (ByVal viewNum As Long) As Long   ' Returns a pointer to a structure
Declare PtrSafe Function mdlWindow_contentRectGetGlobal Lib "stdmdlbltin.dll" (ByRef contentRectP As BSIRect, ByVal windowP As Long) As Long

Type LPoint2d
       X As Long
       Y As Long
End Type

Type BSIRect
       Origin As LPoint2d
       Corner As LPoint2d
End Type

Sub ViewControl()

  Dim windowRect As BSIRect
  Dim lngWindowHeight As Long
  Dim lngWindowWidth As Long
  Dim cornerPoint As LPoint2d
  Dim lngWindowPtr As Long
  
  Dim strArg As String
  If Len(KeyinArguments) > 0 Then
    Dim strArgs() As String
    strArgs = Split(KeyinArguments, " ")
    If LBound(strArgs) > -1 And UBound(strArgs) > -1 Then
      strArg = strArgs(0)
    End If
  End If
  
  ' See if we can get this configuration
  Dim ViewGroup As New Collection
  Set ViewGroup = FindViewConfiguration(strArg)
  
  If ViewGroup.Count = 0 Then
    ' No views defined or not found
    MsgBox "Could not find the View Control Configuration named " & strArg, vbOKOnly, "View Control"
    Exit Sub
  End If
  
  CadInputQueue.SendKeyin "view off all"
  
  Dim highVert As Integer
  Dim highHorz As Integer
  Dim adjVert As Integer
  Dim adjHorz As Integer
  Dim viewConfig As ViewConfiguration
  For Each viewConfig In ViewGroup
    ' Turn on the view
    CadInputQueue.SendKeyin "view on " & CStr(viewConfig.ViewNumber)
    
    ' Try to get the view window
    lngWindowPtr = mdlWindow_viewWindowGet(viewConfig.ViewNumber - 1)
    If lngWindowPtr <> 0 Then
      ' Got the window
      If lngWindowHeight = 0 Then
        ' Haven't set screen dimentions so do that with this window
        CadInputQueue.SendKeyin "window arrange"
        mdlWindow_contentRectGetGlobal windowRect, lngWindowPtr
        lngWindowHeight = windowRect.Corner.Y - windowRect.Origin.Y
        lngWindowWidth = windowRect.Corner.X - windowRect.Origin.X
      End If
      
      ' Adjustments for overlap Top and Left
      If viewConfig.PercentTop = 0 Then
        ' New row so reset adjustment
        adjVert = 0
      Else
        adjVert = 20
      End If
      If viewConfig.PercentLeft = 0 Then
        ' New column so reset adjustment
        adjHorz = 0
      Else
        adjHorz = 8
      End If
      
      ' Set the top left
      cornerPoint.X = windowRect.Origin.X + lngWindowWidth * viewConfig.PercentLeft + adjHorz
      cornerPoint.Y = windowRect.Origin.Y + lngWindowHeight * viewConfig.PercentTop + adjVert
      mdlWindow_resize lngWindowPtr, 0, cornerPoint ' Top left corner (0)
      
      ' Adjustments for overlap Bottom and Right
      If viewConfig.PercentBottom = 1 Then
        ' 100 percent so don't adjust button
        adjVert = 0
      Else
        adjVert = 20
      End If
      If viewConfig.PercentRight = 1 Then
        ' 100 percent so don't adjust right side
        adjHorz = 0
      Else
        adjHorz = 8
      End If
      
      ' Set the bottom right
      cornerPoint.X = windowRect.Origin.X + lngWindowWidth * viewConfig.PercentRight - adjHorz
      cornerPoint.Y = windowRect.Origin.Y + lngWindowHeight * viewConfig.PercentBottom - adjVert
      mdlWindow_resize lngWindowPtr, 2, cornerPoint ' Bottom right corner (2)
    End If
  Next viewConfig
  
End Sub

Function FindViewConfiguration(ConfigurationName As String) As Collection

  ' Set return collection to an empty list
  Set FindViewConfiguration = New Collection
  
  ' Compose the XML file name, based in this VBA's application folder
  Dim strAppPath As String
  strAppPath = GetAppPath
  Dim XmlFileName As String
  XmlFileName = strAppPath & "\ViewControlConfigurations.xml"
  
  If Not fsoActive.FileExists(XmlFileName) Then
    ' Not in app folder so check for configuration variable
    If Application.ActiveWorkspace.IsConfigurationVariableDefined("VIEWSET_SETTINGS_FILE") Then
      XmlFileName = ActiveWorkspace.ConfigurationVariableValue("VIEWSET_SETTINGS_FILE")
      If Not fsoActive.FileExists(XmlFileName) Then
        MsgBox "Could not find the View Control Configurations File (" & XmlFileName & _
               ") defined in the configuration variable (VIEWSET_SETTINGS_FILE)", _
               vbCritical, "View Control"
        Exit Function
      End If
    Else
      MsgBox "Could not find the View Control Configurations File (" & XmlFileName & _
             ") in the application folder, and configuration variable (VIEWSET_SETTINGS_FILE) isn't set", _
             vbCritical, "View Control"
      Exit Function
    End If
  End If

  ' Found the file so load the settings
  Dim i As Long
  Dim strLineIn As String
  Dim strFlds() As String

  Dim xmlDoc As New MSXML2.DOMDocument60
  Dim strAttr As String

  ' Main element
  Dim xmlElmMain As IXMLDOMElement

  On Error GoTo Error
  If xmlDoc.Load(XmlFileName) = True Then
    Set xmlElmMain = xmlDoc.selectSingleNode("ViewControlConfigurations")
    If xmlElmMain Is Nothing Then
      ' Main node not there so bad format
      MsgBox "Invalid View Control Configurations file format (" & XmlFileName & ")", vbInformation
      Exit Function
    End If

    ' Got the Main node so get child nodes
    Dim viewConfigNew As New ViewConfiguration
    Dim xmlElmConfig As IXMLDOMElement
    For Each xmlElmConfig In xmlElmMain.childNodes
      If xmlElmConfig.nodeName = "Configuration" Then
        ' Get the name
        strAttr = Trim(xmlElmConfig.getAttribute("name"))
        If UCase(strAttr) = UCase(ConfigurationName) Then
          ' Found the one we're looking for
          Dim xmlElmView As IXMLDOMElement
          For Each xmlElmView In xmlElmConfig.childNodes
            ' Create a new configuration object and populate its properties
            Set viewConfigNew = New ViewConfiguration
            viewConfigNew.ViewNumber = Val(Trim(xmlElmView.getAttribute("number")))
            viewConfigNew.PercentTop = Val(Trim(xmlElmView.getAttribute("percentTop"))) / 100
            viewConfigNew.PercentBottom = Val(Trim(xmlElmView.getAttribute("percentBottom"))) / 100
            viewConfigNew.PercentLeft = Val(Trim(xmlElmView.getAttribute("percentLeft"))) / 100
            viewConfigNew.PercentRight = Val(Trim(xmlElmView.getAttribute("percentRight"))) / 100
            
            ' Add the new configuration
            FindViewConfiguration.Add viewConfigNew
          Next xmlElmView
          
          ' Found the one we're looking for so stop looking
          Exit For
        End If ' Found a matching name
      End If ' Got configuration node
    Next xmlElmConfig
  Else
    ' Error loading file
    MsgBox "Error loading settings file (" & XmlFileName & ")", vbInformation
    Exit Function
  End If

  ' Close the xml
  Set xmlDoc = Nothing

Error:

End Function

Public Function GetAppPath() As String

  Dim oVBE As VBIDE.VBE
  Dim strPath As String

  ' Get the path where this project was run from for the location of the layout file
  Set oVBE = VBE
  Dim vbProjCurr As VBProject
  For Each vbProjCurr In oVBE.VBProjects
    If vbProjCurr.Name = "ViewSet" Then
      ' This is me so get the path
      strPath = vbProjCurr.FileName
      Exit For
    End If
  Next vbProjCurr

  ' Extract just the path
  If strPath <> "" Then
    GetAppPath = fsoActive.GetParentFolderName(strPath)
  Else
    GetAppPath = "C:"
  End If

End Function

Attribute VB_Name = "ModalDlgHandler"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements IModalDialogEvents

Private Sub IModalDialogEvents_OnDialogClosed(ByVal DialogBoxName As String, ByVal DialogResult As MsdDialogBoxResult)

End Sub

Private Sub IModalDialogEvents_OnDialogOpened(ByVal DialogBoxName As String, DialogResult As MsdDialogBoxResult)

  If DialogBoxName Like "Preferences*" Then
    Dim vwCurr As view

    ' Get the current setting
    Dim intToggle As Integer
    intToggle = GetCExpressionValue("savePrefs.flags.invertBackground", "USERPREF")

    If intToggle = 0 Then
      ' Black background so turn white
      SetCExpressionValue "savePrefs.flags.invertBackground", 1, "USERPREF"
      ' Turn ON Symbology Override in all views
      For Each vwCurr In ActiveDesignFile.Views
        vwCurr.DisplaysLevelSymbology = True
      Next vwCurr
    Else
      ' White background so turn black
      SetCExpressionValue "savePrefs.flags.invertBackground", 0, "USERPREF"
      ' Turn OFF Symbology Override
      For Each vwCurr In ActiveDesignFile.Views
        vwCurr.DisplaysLevelSymbology = False
      Next vwCurr
    End If

    ' Close the dialog box.
    DialogResult = msdDialogBoxResultOK

  End If  ' Preferences [untitled]

End Sub

Attribute VB_Name = "Module1"
Option Explicit

'Declare PtrSafe Function mdlRefFile_getInfo Lib "stdmdlbltin.dll" (ByVal modelRef As LongLong) As LongPtr   ' Returns a pointer to a structure

Sub AccuDrawToggleOnOff()
       
    If MicroStationDGN.CommandState.AccuDrawHints.IsEnabled = True Then
 
        CadInputQueue.SendKeyin "accudraw activate"
        
        CadInputQueue.SendCommand "DMSG ACTIVATETOOLBYPATH Civil AccuDraw\Toggle Civil AccuDraw"
    
        CadInputQueue.SendCommand "CIVILCOORD ACTIVATE "
    
    Else

        CadInputQueue.SendCommand "DMSG ACTIVATETOOLBYPATH Civil AccuDraw\Toggle Civil AccuDraw"
    
        CadInputQueue.SendCommand "CIVILCOORD QUIT "
            
        CadInputQueue.SendKeyin "accudraw activate"
    
    End If
    

End Sub


Sub Toggle()

  ' Add the handler for the preferences dialog
  Dim modalHandler As New ModalDlgHandler
  AddModalDialogEventsHandler modalHandler

  ' The following statement opens modal dialog "Preferences [untitled]"
  ' The handler does the work
  CadInputQueue.SendCommand "MDL SILENTLOAD USERPREF"

  ' Cleanup
  RemoveModalDialogEventsHandler modalHandler
  CommandState.StartDefaultCommand

End Sub


Sub OneView()
  CadInputQueue.SendKeyin "vba run ViewControl Plan"
  CadInputQueue.SendKeyin "view set model ""Default"" 1"
End Sub

Sub TwoView()

  CadInputQueue.SendKeyin "vba run ViewControl PlanProfile"
  CadInputQueue.SendKeyin "view set model ""Default"" 1"
  
  CadInputQueue.SendCommand "CHOOSE NONE"
     

End Sub

Sub FourView()
  
  ' Open Views 1,3,5 and 7.  1 = Plan, 3 = 3D Model, 5 = Profile, 7 = XS
  CadInputQueue.SendKeyin "vba run ViewControl FourSquare"
  CadInputQueue.SendKeyin "view set model ""Default"" 1"
  CadInputQueue.SendKeyin "MDL KEYIN BENTLEY.VIEWATTRIBUTESDIALOG,VAD VIEWATTRIBUTESDIALOG SETATTRIBUTE 4 Grid True"
  CadInputQueue.SendKeyin "MDL KEYIN BENTLEY.VIEWATTRIBUTESDIALOG,VAD VIEWATTRIBUTESDIALOG SETATTRIBUTE 6 Grid True"
    
  ' Try to find the 3D model for the active model and assign to View 3
  Dim strModName3D As String
  strModName3D = ActiveModelReference.Name & "-3D"
  Dim blnFound As Boolean
  blnFound = False
  Dim modRefCurr As ModelReference
  For Each modRefCurr In ActiveDesignFile.Models
    If UCase(modRefCurr.Name) = UCase(strModName3D) Then
      ' Found it
      blnFound = True
      CadInputQueue.SendKeyin "view set model """ & modRefCurr.Name & """ 3"
    ' Stop looking
      Exit For
    End If
  Next modRefCurr
  If Not blnFound Then
    ' Didn't find the standard one so set view 3 to the first "*-3D" model found
    For Each modRefCurr In ActiveDesignFile.Models
      If UCase(Right(modRefCurr.Name, 3)) = "-3D" Then
        ' Found one so use it
        blnFound = True
        CadInputQueue.SendKeyin "view set model """ & modRefCurr.Name & """ 3"
      ' Stop looking
        Exit For
      End If
    Next modRefCurr
  End If
  If Not blnFound Then
    ' Didn't find a model with "-3D" at the end so set view 3 to the first 3D model found
    For Each modRefCurr In ActiveDesignFile.Models
      If modRefCurr.Is3D Then
        ' Found one so use it
        blnFound = True
        CadInputQueue.SendKeyin "view set model """ & modRefCurr.Name & """ 3"
      ' Stop looking
        Exit For
      End If
    Next modRefCurr
  End If

  ' Set view 3 to Smooth
  ' CadInputQueue.SendKeyin "CHANGE VIEW CUSTOM ""Smooth"" 3"
  CadInputQueue.SendKeyin "CHANGE VIEW CUSTOM ""Illustration:Ignore Lighting"" 3"
  CadInputQueue.SendKeyin "MDL KEYIN BENTLEY.VIEWATTRIBUTESDIALOG,VAD VIEWATTRIBUTESDIALOG SETATTRIBUTE 3 ClipVolume False "
  

  ' Set view 3 to the same range as view 1
  ActiveDesignFile.Views(1).Select
  Dim vwOne As view
  Set vwOne = ActiveDesignFile.Views(1)
  Dim vwTwo As view
  Set vwTwo = ActiveDesignFile.Views(3)
  vwTwo.Rotation = Matrix3dIdentity
  On Error Resume Next
  vwTwo.Fit True
  On Error GoTo 0
  ' Adjust extents and origin for 3D
  Dim pntExtents As Point3d
  pntExtents = vwOne.Extents
  pntExtents.Z = vwTwo.Extents.Z
  Dim pntOrigin As Point3d
  pntOrigin = vwOne.Origin
  pntOrigin.Z = vwTwo.Origin.Z
  vwTwo.SetArea pntOrigin, pntExtents, vwOne.Rotation, vwOne.ActiveDepth
  ' Get the average element elevation in the view and set the center to that
  Dim dblAvgElev As Double
  dblAvgElev = GetViewElementsAverageElevation(vwTwo)
  ' Rotate up 60 degrees about the X axis
  vwTwo.Rotation = Matrix3dFromAxisAndRotationAngle(0, -1 * Pi / 3)
  vwTwo.Center = Point3dFromXYZ(vwOne.Center.X, vwOne.Center.Y, dblAvgElev)
  
  vwTwo.ClipVolume = True
  vwTwo.ClipFront = False
  vwTwo.ClipBack = False
  
  vwTwo.Redraw
  ActiveDesignFile.Views(3).Select
  
  ' Make View 1 active
  ActiveDesignFile.Views(1).Select
  CadInputQueue.SendCommand "CHOOSE NONE"
  
    
 'Execute the Open Profile Model Command
  Dim dlgResult As VbMsgBoxResult
  dlgResult = MsgBox("Select OK to Create a Dynamic Profile View", vbOKCancel, "Open a Dynamic Profile View")
  If dlgResult = 1 Then
    Call OpenProfileModel
  End If
  
  
  'Execute the Open DynamicXS Model Command
   dlgResult = MsgBox("Select OK to Create a Dynamic XS View", vbOKCancel, "Open a Dynamic Cross Section View")
   If dlgResult = 1 Then
     Call OpenDynamicXSModel
   End If


End Sub

Sub TwoView3D()

  CadInputQueue.SendKeyin "vba run ViewControl Plan3D"
  CadInputQueue.SendKeyin "view set model ""Default"" 1"
  
  ' Try to find the 3D model for the active model
  Dim strModName3D As String
  strModName3D = ActiveModelReference.Name & "-3D"
  Dim blnFound As Boolean
  blnFound = False
  Dim modRefCurr As ModelReference
  For Each modRefCurr In ActiveDesignFile.Models
    If UCase(modRefCurr.Name) = UCase(strModName3D) Then
      ' Found it
      blnFound = True
      CadInputQueue.SendKeyin "view set model """ & modRefCurr.Name & """ 2"
    ' Stop looking
      Exit For
    End If
  Next modRefCurr
  If Not blnFound Then
    ' Didn't find the standard one so set view 2 to the first "*-3D" model found
    For Each modRefCurr In ActiveDesignFile.Models
      If UCase(Right(modRefCurr.Name, 3)) = "-3D" Then
        ' Found one so use it
        blnFound = True
        CadInputQueue.SendKeyin "view set model """ & modRefCurr.Name & """ 2"
        ' Stop looking
        Exit For
      End If
    Next modRefCurr
  End If
  If Not blnFound Then
    ' Didn't find a model with "-3D" at the end so set view 2 to the first 3D model found
    For Each modRefCurr In ActiveDesignFile.Models
      If modRefCurr.Is3D Then
        ' Found one so use it
        blnFound = True
        CadInputQueue.SendKeyin "view set model """ & modRefCurr.Name & """ 2"
        ' Stop looking
        Exit For
      End If
    Next modRefCurr
  End If

  ' Set view 2 to Smooth
  ' CadInputQueue.SendKeyin "CHANGE VIEW CUSTOM ""Smooth"" 2"
  CadInputQueue.SendKeyin "CHANGE VIEW CUSTOM ""Illustration:Ignore Lighting"" 2"
  CadInputQueue.SendKeyin "MDL KEYIN BENTLEY.VIEWATTRIBUTESDIALOG,VAD VIEWATTRIBUTESDIALOG SETATTRIBUTE 2 ClipVolume False "

  ' Set view 2 to the same range as view 1
  Dim vwOne As view
  Set vwOne = ActiveDesignFile.Views(1)
  Dim vwTwo As view
  Set vwTwo = ActiveDesignFile.Views(2)
  vwTwo.Rotation = Matrix3dIdentity
  On Error Resume Next
  vwTwo.Fit True
  On Error GoTo 0
  ' Adjust extents and origin for 3D
  Dim pntExtents As Point3d
  pntExtents = vwOne.Extents
  pntExtents.Z = vwTwo.Extents.Z
  Dim pntOrigin As Point3d
  pntOrigin = vwOne.Origin
  pntOrigin.Z = vwTwo.Origin.Z
  vwTwo.SetArea pntOrigin, pntExtents, vwOne.Rotation, vwOne.ActiveDepth
  ' Get the average element elevation in the view and set the center to that
  Dim dblAvgElev As Double
  dblAvgElev = GetViewElementsAverageElevation(vwTwo)
  ' Rotate up 60 degrees about the X axis
  vwTwo.Rotation = Matrix3dFromAxisAndRotationAngle(0, -1 * Pi / 3)
  vwTwo.Center = Point3dFromXYZ(vwOne.Center.X, vwOne.Center.Y, dblAvgElev)
  
  vwTwo.ClipVolume = True
  vwTwo.ClipFront = False
  vwTwo.ClipBack = False
  
  vwTwo.Redraw
  ActiveDesignFile.Views(2).Select

  ' Make View 1 active
  ActiveDesignFile.Views(1).Select
  CadInputQueue.SendCommand "CHOOSE NONE"

End Sub

Sub TwoView3DF9()

  CadInputQueue.SendKeyin "vba run ViewControl Plan3D"
  CadInputQueue.SendKeyin "view set model ""Default"" 1"
  
  ' Try to find the 3D model for the active model
  Dim strModName3D As String
  strModName3D = ActiveModelReference.Name & "-3D"
  Dim blnFound As Boolean
  blnFound = False
  Dim modRefCurr As ModelReference
  For Each modRefCurr In ActiveDesignFile.Models
    If UCase(modRefCurr.Name) = UCase(strModName3D) Then
      ' Found it
      blnFound = True
      CadInputQueue.SendKeyin "view set model """ & modRefCurr.Name & """ 2"
    ' Stop looking
      Exit For
    End If
  Next modRefCurr
  If Not blnFound Then
    ' Didn't find the standard one so set view 2 to the first "*-3D" model found
    For Each modRefCurr In ActiveDesignFile.Models
      If UCase(Right(modRefCurr.Name, 3)) = "-3D" Then
        ' Found one so use it
        blnFound = True
        CadInputQueue.SendKeyin "view set model """ & modRefCurr.Name & """ 2"
        ' Stop looking
        Exit For
      End If
    Next modRefCurr
  End If
  If Not blnFound Then
    ' Didn't find a model with "-3D" at the end so set view 2 to the first 3D model found
    For Each modRefCurr In ActiveDesignFile.Models
      If modRefCurr.Is3D Then
        ' Found one so use it
        blnFound = True
        CadInputQueue.SendKeyin "view set model """ & modRefCurr.Name & """ 2"
        ' Stop looking
        Exit For
      End If
    Next modRefCurr
  End If

  ' Set view 2 to illustration -ignore lighting
  CadInputQueue.SendKeyin "CHANGE VIEW CUSTOM ""Illustration:Ignore Lighting"" 2"
  CadInputQueue.SendKeyin "MDL KEYIN BENTLEY.VIEWATTRIBUTESDIALOG,VAD VIEWATTRIBUTESDIALOG SETATTRIBUTE 2 ClipVolume False "

  ' Set view 2 to the same range as view 1
  Dim vwOne As view
  Set vwOne = ActiveDesignFile.Views(1)
  Dim vwTwo As view
  Set vwTwo = ActiveDesignFile.Views(2)
  vwTwo.Rotation = Matrix3dIdentity
  On Error Resume Next
  vwTwo.Fit True
  On Error GoTo 0
  ' Adjust extents and origin for 3D
  Dim pntExtents As Point3d
  pntExtents = vwOne.Extents
  pntExtents.Z = vwTwo.Extents.Z
  Dim pntOrigin As Point3d
  pntOrigin = vwOne.Origin
  pntOrigin.Z = vwTwo.Origin.Z
  vwTwo.SetArea pntOrigin, pntExtents, vwOne.Rotation, vwOne.ActiveDepth
  ' Get the average element elevation in the view and set the center to that
  Dim dblAvgElev As Double
  dblAvgElev = GetViewElementsAverageElevation(vwTwo)
  ' Rotate up 60 degrees about the X axis
  vwTwo.Rotation = Matrix3dFromAxisAndRotationAngle(0, -1 * Pi / 3)
  vwTwo.Center = Point3dFromXYZ(vwOne.Center.X, vwOne.Center.Y, dblAvgElev)
  
  vwTwo.ClipVolume = True
  vwTwo.ClipFront = False
  vwTwo.ClipBack = False
  
  vwTwo.Redraw
  ActiveDesignFile.Views(2).Select

  ' Make View 1 active
  ActiveDesignFile.Views(1).Select
  CadInputQueue.SendCommand "CHOOSE NONE"

End Sub


Function GetViewElementsAverageElevation(View3D As view) As Double

  ' Get a fence from the view
  Dim pts(1 To 4) As Point2d
  Dim size As Point3d
  size = View3D.Extents
  pts(2).Y = size.Y
  pts(3).X = size.X
  pts(3).Y = size.Y
  pts(4).X = size.X
  ActiveDesignFile.Fence.DefineFromViewPoints View3D, pts

  ' Get the elements in the fence (inside)
  Dim elmEnum As ElementEnumerator
  ActiveSettings.FenceClip = False
  ActiveSettings.FenceOverlap = True
  ActiveSettings.FenceVoid = False
  Set elmEnum = ActiveDesignFile.Fence.GetContents
  Dim lngElmCnt As Long
  Dim dblElmElevSum As Double
  Do While elmEnum.MoveNext
    lngElmCnt = lngElmCnt + 1
    Dim dblElmElevAvg As Double
    dblElmElevAvg = (elmEnum.Current.Range.Low.Z + elmEnum.Current.Range.High.Z) / 2
    dblElmElevSum = dblElmElevSum + dblElmElevAvg
  Loop
  
  If lngElmCnt > 0 Then
    ' Compute the average
    GetViewElementsAverageElevation = dblElmElevSum / lngElmCnt
  Else
    ' No elements so use the view center
    GetViewElementsAverageElevation = View3D.Center.Z
  End If

End Function

Sub ToggleViewConstructions()

  ' Toggle constructions in current view
  Dim i As Integer
  For i = 1 To 8
    If ActiveDesignFile.Views.Item(i).IsSelected Then
      ' Toggle this one and quit looking
      ActiveDesignFile.Views.Item(i).DisplaysConstructions = Not ActiveDesignFile.Views.Item(i).DisplaysConstructions
      ActiveDesignFile.Views.Item(i).Redraw
      Exit For
    End If
  Next i
  'CursorInformation.CurrentView.DisplaysConstructions = Not CursorInformation.CurrentView.DisplaysConstructions
  'CursorInformation.CurrentView.Redraw

End Sub

Sub ToggleViewLineWeights()

  ' Toggle weights in current view
  Dim i As Integer
  For i = 1 To 8
    If ActiveDesignFile.Views.Item(i).IsSelected Then
      ' Toggle this one and quit looking
      ActiveDesignFile.Views.Item(i).DisplaysLineWeights = Not ActiveDesignFile.Views.Item(i).DisplaysLineWeights
      ActiveDesignFile.Views.Item(i).Redraw
      Exit For
    End If
  Next i
  'CursorInformation.CurrentView.DisplaysConstructions = Not CursorInformation.CurrentView.DisplaysConstructions
  'CursorInformation.CurrentView.Redraw

End Sub

Sub DeleteUnusedFonts()

    Dim startPoint As Point3d
    Dim point As Point3d, point2 As Point3d
    Dim lngTemp As Long
'   Send a keyin that can be a command string
    CadInputQueue.SendKeyin "delete unused fonts"
    CadInputQueue.SendKeyin "file disassociateworkset"
'   Start a command
    CadInputQueue.SendCommand "FILEDESIGN"
    CadInputQueue.SendCommand "COMPRESS DESIGN CONFIRM"

End Sub

Sub SetActiveModelToDrawLast()

  ' Shift attachments
  Dim i As Long
  For i = ActiveModelReference.Attachments.Count To 1 Step -1
    ActiveModelReference.Attachments(i).UpdateOrder = 0
  Next i

  ' Set the color adjustment factor
  If ActiveModelReference.Attachments.Count > 0 Then
    ' Get the first attachment to compare
    Dim attCurr As Attachment
    Set attCurr = ActiveModelReference.Attachments(1)

    ' Compose the C expression to access the referenceFile C struct
'    Dim lngModRefP As Variant
'    lngModRefP = attCurr.MdlModelRefP
'    Dim lngRefStruct As LongPtr
'    lngRefStruct = mdlRefFile_getInfo(lngModRefP)
'    Dim refName As String
'    refName = "((struct referenceFile *)" & lngRefStruct & ")"
''    refName = "((struct referenceFile *)" & lngModRefP & ")"
'
'    Dim lngValueAdj As Long
'    Dim lngSaturAdj As Long
'
'    ' Get the current values
'    lngValueAdj = GetCExpressionValue(refName & "->display.hsvValueAdjustment")
'    lngSaturAdj = GetCExpressionValue(refName & "->display.hsvSaturationAdjustment")
'
'    ' Toggle the color adjustment factor for all references
'    If lngValueAdj = 0 And lngSaturAdj = 0 Then
'      CadInputQueue.SendKeyin "reference adjustcolors 30,50 *"
'    Else
'      CadInputQueue.SendKeyin "reference adjustcolors 100,100 *"
'    End If
'    CadInputQueue.SendCommand "FILEDESIGN"
    ' Toggle the color adjustment factor for all references
    If Not attCurr.PrintColorAdjustment Then
      CadInputQueue.SendKeyin "reference adjustcolors 30,50 *"
      attCurr.PrintColorAdjustment = True
    Else
      CadInputQueue.SendKeyin "reference adjustcolors 100,100 *"
      attCurr.PrintColorAdjustment = False
    End If
    CadInputQueue.SendCommand "FILEDESIGN"
  End If

End Sub

Sub AnalyzeTerrainModelPoint()

    Dim startPoint As Point3d
    Dim point As Point3d, point2 As Point3d
    Dim lngTemp As Long

'   Start a command
    CadInputQueue.SendCommand "DMSG ACTIVATETOOLBYPATH Civil AccuDraw\Toggle Civil AccuDraw"

    CadInputQueue.SendCommand "CIVILCOORD ACTIVATE "

    CadInputQueue.SendCommand "DMSG ACTIVATETOOLBYPATH Civil AccuDraw\Station-Offset"

    CadInputQueue.SendCommand "TERRAINMODEL ANALYZE POINT"

End Sub

Sub ExaggerateZForAttachment()

  ' Make sure the model doesn't already exist
  Dim modCurr As ModelReference
  For Each modCurr In ActiveDesignFile.Models
    If modCurr.Name = "3D Temporary Visualization" Then
      ' Found one so remove it
      ActiveDesignFile.Models.Delete modCurr
      Exit For
    End If
  Next modCurr

'  Dim intViewNum As Integer
'  intViewNum = CursorInformation.CurrentView.Index

  ' Save the original model to return to when dialog is closed
  Set frmExaggerateZ.OriginalModel = ActiveModelReference

  ' Create new model
  Dim modRefTemp As ModelReference
  Set modRefTemp = ActiveDesignFile.Models.Add(ActiveModelReference, "3D Temporary Visualization", "Temporary model for visualizing exaggerated verticals", msdModelTypeNormal, True)

  ' Switch to model and attach the current model as a reference
  Dim strInitialModel As String
  strInitialModel = ActiveModelReference.Name
  modRefTemp.Activate
  Dim attTemp As Attachment
  Set attTemp = modRefTemp.Attachments.Add(ActiveDesignFile.FullName, strInitialModel, "Temp3DVis", "3D Temporary Visualization", Point3dZero, Point3dZero)

  ' Fit the first view
  On Error Resume Next
  Dim i As Integer
  For i = 1 To 8
    If ActiveDesignFile.Views(i).IsOpen Then
    If ActiveDesignFile.Views(i).IsSelected Then
      ActiveDesignFile.Views(i).Maximize
      ActiveDesignFile.Views(i).Fit True
      ActiveDesignFile.Views(i).Redraw
    Else
      ActiveDesignFile.Views(i).IsOpen = False
    End If
    End If
  Next i
  On Error GoTo 0
'  CursorInformation.CurrentView.Fit True
'  CursorInformation.CurrentView.Redraw
'  ActiveDesignFile.Views(intViewNum).Fit True
'  ActiveDesignFile.Views(intViewNum).Redraw

  ' Disclaimer
  MsgBox "Note: Visual Inspection Aid Only.  Elevation Values Will Be Shifted.", vbInformation, "Exaggerate Z For Attachment"

  ' Set the temporary model to remove when dialog is closed
  Set frmExaggerateZ.TempModel = modRefTemp

  ' Show the dialog
  frmExaggerateZ.Show

End Sub

Sub ThreeViewsPLPROF3D()
  
  CadInputQueue.SendKeyin "vba run ViewControl PlanProf3D"
  CadInputQueue.SendKeyin "view set model ""Default"" 1"
  CadInputQueue.SendKeyin "MDL KEYIN BENTLEY.VIEWATTRIBUTESDIALOG,VAD VIEWATTRIBUTESDIALOG SETATTRIBUTE 3 Grid True"
   
' Try to find the 3D model for the active model and assign to View 3
  Dim strModName3D As String
  strModName3D = ActiveModelReference.Name & "-3D"
  Dim blnFound As Boolean
  blnFound = False
  Dim modRefCurr As ModelReference
  For Each modRefCurr In ActiveDesignFile.Models
    If UCase(modRefCurr.Name) = UCase(strModName3D) Then
      ' Found it
      blnFound = True
      CadInputQueue.SendKeyin "view set model """ & modRefCurr.Name & """ 3"
    ' Stop looking
      Exit For
    End If
  Next modRefCurr
  If Not blnFound Then
    ' Didn't find the standard one so set view 3 to the first "*-3D" model found
    For Each modRefCurr In ActiveDesignFile.Models
      If UCase(Right(modRefCurr.Name, 3)) = "-3D" Then
        ' Found one so use it
        blnFound = True
        CadInputQueue.SendKeyin "view set model """ & modRefCurr.Name & """ 3"
      ' Stop looking
        Exit For
      End If
    Next modRefCurr
  End If
  If Not blnFound Then
    ' Didn't find a model with "-3D" at the end so set view 3 to the first 3D model found
    For Each modRefCurr In ActiveDesignFile.Models
      If modRefCurr.Is3D Then
        ' Found one so use it
        blnFound = True
        CadInputQueue.SendKeyin "view set model """ & modRefCurr.Name & """ 3"
      ' Stop looking
        Exit For
      End If
    Next modRefCurr
  End If

  ' Set view 3 to Smooth
  ' CadInputQueue.SendKeyin "CHANGE VIEW CUSTOM ""Smooth"" 3"
  CadInputQueue.SendKeyin "CHANGE VIEW CUSTOM ""Illustration:Ignore Lighting"" 3"
  CadInputQueue.SendKeyin "MDL KEYIN BENTLEY.VIEWATTRIBUTESDIALOG,VAD VIEWATTRIBUTESDIALOG SETATTRIBUTE 3 ClipVolume False "

  ' Set view 3 to the same range as view 1
  Dim vwOne As view
  Set vwOne = ActiveDesignFile.Views(1)
  Dim vwTwo As view
  Set vwTwo = ActiveDesignFile.Views(3)
  vwTwo.Rotation = Matrix3dIdentity
  On Error Resume Next
  vwTwo.Fit True
  On Error GoTo 0
  ' Adjust extents and origin for 3D
  Dim pntExtents As Point3d
  pntExtents = vwOne.Extents
  pntExtents.Z = vwTwo.Extents.Z
  Dim pntOrigin As Point3d
  pntOrigin = vwOne.Origin
  pntOrigin.Z = vwTwo.Origin.Z
  vwTwo.SetArea pntOrigin, pntExtents, vwOne.Rotation, vwOne.ActiveDepth
  ' Get the average element elevation in the view and set the center to that
  Dim dblAvgElev As Double
  dblAvgElev = GetViewElementsAverageElevation(vwTwo)
  ' Rotate up 60 degrees about the X axis
  vwTwo.Rotation = Matrix3dFromAxisAndRotationAngle(0, -1 * Pi / 3)
  vwTwo.Center = Point3dFromXYZ(vwOne.Center.X, vwOne.Center.Y, dblAvgElev)
  
  vwTwo.ClipVolume = True
  vwTwo.ClipFront = False
  vwTwo.ClipBack = False
  
  vwTwo.Redraw
  ActiveDesignFile.Views(3).Select

  ' Make View 1 active
  ActiveDesignFile.Views(1).Select
  CadInputQueue.SendCommand "UPDATE VIEW EXTENDED 1"
  ' CadInputQueue.SendCommand "FILEDESIGN"
  CadInputQueue.SendCommand "CHOOSE NONE"
  
  'Execute the Open Profile Model Command
  Dim dlgResult As VbMsgBoxResult
  dlgResult = MsgBox("Select OK to Create a Dynamic Profile View", vbOKCancel, "Open a Dynamic Profile View")
  If dlgResult = 1 Then
    Call OpenProfileModel
  End If

End Sub

Sub ThreeViewsPLXS3D()
  
  
' Open Views 1,3, and 7.  1 = Plan, 3 = 3D Model, 7 = XS
  CadInputQueue.SendKeyin "vba run ViewControl PlanXS3D"
  CadInputQueue.SendKeyin "view set model ""Default"" 1"
  CadInputQueue.SendKeyin "MDL KEYIN BENTLEY.VIEWATTRIBUTESDIALOG,VAD VIEWATTRIBUTESDIALOG SETATTRIBUTE 6 Grid True"
   
' Try to find the 3D model for the active model and assign to View 3
  Dim strModName3D As String
  strModName3D = ActiveModelReference.Name & "-3D"
  Dim blnFound As Boolean
  blnFound = False
  Dim modRefCurr As ModelReference
  For Each modRefCurr In ActiveDesignFile.Models
    If UCase(modRefCurr.Name) = UCase(strModName3D) Then
      ' Found it
      blnFound = True
      CadInputQueue.SendKeyin "view set model """ & modRefCurr.Name & """ 3"
    ' Stop looking
      Exit For
    End If
  Next modRefCurr
  If Not blnFound Then
    ' Didn't find the standard one so set view 3 to the first "*-3D" model found
    For Each modRefCurr In ActiveDesignFile.Models
      If UCase(Right(modRefCurr.Name, 3)) = "-3D" Then
        ' Found one so use it
        blnFound = True
        CadInputQueue.SendKeyin "view set model """ & modRefCurr.Name & """ 3"
      ' Stop looking
        Exit For
      End If
    Next modRefCurr
  End If
  If Not blnFound Then
    ' Didn't find a model with "-3D" at the end so set view 3 to the first 3D model found
    For Each modRefCurr In ActiveDesignFile.Models
      If modRefCurr.Is3D Then
        ' Found one so use it
        blnFound = True
        CadInputQueue.SendKeyin "view set model """ & modRefCurr.Name & """ 3"
      ' Stop looking
        Exit For
      End If
    Next modRefCurr
  End If

  ' Set view 3 to Smooth
  ' CadInputQueue.SendKeyin "CHANGE VIEW CUSTOM ""Smooth"" 3"
  CadInputQueue.SendKeyin "CHANGE VIEW CUSTOM ""Illustration:Ignore Lighting"" 3"
  CadInputQueue.SendKeyin "MDL KEYIN BENTLEY.VIEWATTRIBUTESDIALOG,VAD VIEWATTRIBUTESDIALOG SETATTRIBUTE 3 ClipVolume False "

  ' Set view 3 to the same range as view 1
  Dim vwOne As view
  Set vwOne = ActiveDesignFile.Views(1)
  Dim vwTwo As view
  Set vwTwo = ActiveDesignFile.Views(3)
  vwTwo.Rotation = Matrix3dIdentity
  On Error Resume Next
  vwTwo.Fit True
  On Error GoTo 0
  ' Adjust extents and origin for 3D
  Dim pntExtents As Point3d
  pntExtents = vwOne.Extents
  pntExtents.Z = vwTwo.Extents.Z
  Dim pntOrigin As Point3d
  pntOrigin = vwOne.Origin
  pntOrigin.Z = vwTwo.Origin.Z
  vwTwo.SetArea pntOrigin, pntExtents, vwOne.Rotation, vwOne.ActiveDepth
  ' Get the average element elevation in the view and set the center to that
  Dim dblAvgElev As Double
  dblAvgElev = GetViewElementsAverageElevation(vwTwo)
  ' Rotate up 60 degrees about the X axis
  vwTwo.Rotation = Matrix3dFromAxisAndRotationAngle(0, -1 * Pi / 3)
  vwTwo.Center = Point3dFromXYZ(vwOne.Center.X, vwOne.Center.Y, dblAvgElev)
  
  vwTwo.ClipVolume = True
  vwTwo.ClipFront = False
  vwTwo.ClipBack = False
  
  vwTwo.Redraw
  ActiveDesignFile.Views(3).Select

  ' Make View 1 active
  ActiveDesignFile.Views(1).Select
  CadInputQueue.SendCommand "UPDATE VIEW EXTENDED 1"
  ' CadInputQueue.SendCommand "FILEDESIGN"
  CadInputQueue.SendCommand "CHOOSE NONE"
  
    
  'Execute the Open DynamicXS Model Command
   Dim dlgResult As VbMsgBoxResult
   dlgResult = MsgBox("Select OK to Create a Dynamic XS View", vbOKCancel, "Open a Dynamic Cross Section View")
   If dlgResult = 1 Then
     Call OpenDynamicXSModel
   End If
    
End Sub

Sub TwoViewsPLPROF()
  
' Open Views 1 and 4.  1 = Plan, 4 = Profile
  CadInputQueue.SendKeyin "vba run ViewControl PlanProfile"
  CadInputQueue.SendKeyin "view set model ""Default"" 1"
  CadInputQueue.SendKeyin "MDL KEYIN BENTLEY.VIEWATTRIBUTESDIALOG,VAD VIEWATTRIBUTESDIALOG SETATTRIBUTE 3 Grid True"
   
' Make View 1 active
  ActiveDesignFile.Views(1).Select
  CadInputQueue.SendCommand "CHOOSE NONE"
  
  'Execute the Open Profile Model Command
  Dim dlgResult As VbMsgBoxResult
  dlgResult = MsgBox("Select OK to Create a Dynamic Profile View", vbOKCancel, "Open a Dynamic Profile View")
  If dlgResult = 1 Then
    Call OpenProfileModel
  End If

End Sub

Sub OpenProfileModel()

  CadInputQueue.SendCommand "GEOMETRY PROFILE OPEN VIEW"
  
  Dim intPointsIssued As Integer
  intPointsIssued = 0

  Dim pntPrev As Point3d
  pntPrev = CommandState.LastDataPoint
  Dim pntCurr As Point3d

  Dim timeNow As Date
  Dim timeStart As Date
  timeStart = Now
  
  Dim dblTimeElapsed As Double
  dblTimeElapsed = Now() - timeStart
  
  ' Wait for two data points or 30 seconds, which ever comes first
  Do While intPointsIssued < 2 And dblTimeElapsed < 20
    ' Wait two seconds, allowing other processes to run
    timeNow = Now()
    Do While DateDiff("s", timeNow, Now()) < 2
      DoEvents
    Loop
    
    ' Get the last data point issued
    pntCurr = CommandState.LastDataPoint
    If Not Point3dEqual(pntCurr, pntPrev) Then
      ' Point changed
      intPointsIssued = intPointsIssued + 1
      pntPrev = pntCurr
    End If
    
    ' Get the change in time
    dblTimeElapsed = DateDiff("s", timeStart, Now())
  Loop
  
  If intPointsIssued <= 2 And dblTimeElapsed < 20 Then
  ' Wait two seconds, allowing other processes to run
    timeNow = Now()
    Do While DateDiff("s", timeNow, Now()) < 1
      DoEvents
    Loop
    CadInputQueue.SendCommand "CHOOSE NONE"
  
  Else
      CadInputQueue.SendCommand "CHOOSE NONE"
  End If

End Sub

Sub TwoViewsPLSE()

' Open Views 1 and 8.  1 = Plan, 8 = Superelevation
  
  CadInputQueue.SendKeyin "vba run ViewControl PlanSE"
  CadInputQueue.SendKeyin "view set model ""Default"" 1"
  CadInputQueue.SendKeyin "MDL KEYIN BENTLEY.VIEWATTRIBUTESDIALOG,VAD VIEWATTRIBUTESDIALOG SETATTRIBUTE 7 Grid True"
    
  CadInputQueue.SendCommand "CHOOSE NONE"
  
  'Execute the Open Superelevation Model Command
  Dim dlgResult As VbMsgBoxResult
  dlgResult = MsgBox("Select OK to Create a Dynamic Superelevation View", vbOKCancel, "Open a Dynamic Superelevation View")
  If dlgResult = 1 Then
    Call OpenDynamicSuperelevationView
  End If

End Sub

Sub TwoViewsPLXS()
  
' Open Views 1 and 8.  1 = Plan, 8 = XS
  CadInputQueue.SendKeyin "vba run ViewControl PlanXS"
  CadInputQueue.SendKeyin "view set model ""Default"" 1"
  CadInputQueue.SendKeyin "MDL KEYIN BENTLEY.VIEWATTRIBUTESDIALOG,VAD VIEWATTRIBUTESDIALOG SETATTRIBUTE 7 Grid True"
  
  
  'Execute the Open DynamicXS Model Command
   Dim dlgResult As VbMsgBoxResult
   dlgResult = MsgBox("Select OK to Create a Dynamic XS View", vbOKCancel, "Open a Dynamic Cross Section View")
   If dlgResult = 1 Then
     Call OpenDynamicXSModel
   End If

End Sub

Sub ThreeViewsPLPROFXS()
  
' Open Views 1,5 and 7.  1 = Plan, 5 = Profile, 7 = XS
  CadInputQueue.SendKeyin "vba run ViewControl PlanProfileXS"
  CadInputQueue.SendKeyin "view set model ""Default"" 1"
  CadInputQueue.SendKeyin "MDL KEYIN BENTLEY.VIEWATTRIBUTESDIALOG,VAD VIEWATTRIBUTESDIALOG SETATTRIBUTE 4 Grid True"
  CadInputQueue.SendKeyin "MDL KEYIN BENTLEY.VIEWATTRIBUTESDIALOG,VAD VIEWATTRIBUTESDIALOG SETATTRIBUTE 6 Grid True"
  
  ' Make View 1 active
  ActiveDesignFile.Views(1).Select
  CadInputQueue.SendCommand "CHOOSE NONE"
  
  'Execute the Open Profile Model Command
  Dim dlgResult As VbMsgBoxResult
  dlgResult = MsgBox("Select OK to Create a Dynamic Profile View", vbOKCancel, "Open a Dynamic Profile View")
  If dlgResult = 1 Then
    Call OpenProfileModel
  End If
  
  'Execute the Open DynamicXS Model Command
   dlgResult = MsgBox("Select OK to Create a Dynamic XS View", vbOKCancel, "Open a Dynamic Cross Section View")
   If dlgResult = 1 Then
     Call OpenDynamicXSModel
   End If

End Sub

Sub ThreeViewsPLSuperXS()
  
' Open Views 1,5 and 7.  1 = Plan, 5 = Superelevation, 7 = XS
  CadInputQueue.SendKeyin "vba run ViewControl PlanSuperXS"
  CadInputQueue.SendKeyin "view set model ""Default"" 1"
  CadInputQueue.SendKeyin "MDL KEYIN BENTLEY.VIEWATTRIBUTESDIALOG,VAD VIEWATTRIBUTESDIALOG SETATTRIBUTE 4 Grid True"
  CadInputQueue.SendKeyin "MDL KEYIN BENTLEY.VIEWATTRIBUTESDIALOG,VAD VIEWATTRIBUTESDIALOG SETATTRIBUTE 6 Grid True"
    
  ' Make View 1 active
  ActiveDesignFile.Views(1).Select
  CadInputQueue.SendCommand "CHOOSE NONE"
  
 'Execute the Open Superelevation Model Command
  Dim dlgResult As VbMsgBoxResult
  dlgResult = MsgBox("Select OK to Create a Dynamic Superelevation View", vbOKCancel, "Open a Dynamic Superelevation View")
  If dlgResult = 1 Then
    Call OpenDynamicSuperelevationView
  End If

'Execute the Open DynamicXS Model Command
   dlgResult = MsgBox("Select OK to Create a Dynamic XS View", vbOKCancel, "Open a Dynamic Cross Section View")
   If dlgResult = 1 Then
     Call OpenDynamicXSModel
   End If


End Sub


Sub OpenDynamicXSModel()

  CadInputQueue.SendCommand "GEOMETRY CROSSSECTION OPEN VIEW"
  
End Sub

Sub OpenDynamicSuperelevationView()

  CadInputQueue.SendCommand "GEOMETRY SUPERELEVATION OPEN VIEW"
  
  Dim intPointsIssued As Integer
  intPointsIssued = 0

  Dim pntPrev As Point3d
  pntPrev = CommandState.LastDataPoint
  Dim pntCurr As Point3d

  Dim timeNow As Date
  Dim timeStart As Date
  timeStart = Now
  
  Dim dblTimeElapsed As Double
  dblTimeElapsed = Now() - timeStart
  
  ' Wait for two data points or 30 seconds, which ever comes first
  Do While intPointsIssued < 2 And dblTimeElapsed < 20
    ' Wait two seconds, allowing other processes to run
    timeNow = Now()
    Do While DateDiff("s", timeNow, Now()) < 2
      DoEvents
    Loop
    
    ' Get the last data point issued
    pntCurr = CommandState.LastDataPoint
    If Not Point3dEqual(pntCurr, pntPrev) Then
      ' Point changed
      intPointsIssued = intPointsIssued + 1
      pntPrev = pntCurr
    End If
    
    ' Get the change in time
    dblTimeElapsed = DateDiff("s", timeStart, Now())
  Loop
  
  If intPointsIssued <= 2 And dblTimeElapsed < 20 Then
  ' Wait two seconds, allowing other processes to run
    timeNow = Now()
    Do While DateDiff("s", timeNow, Now()) < 1
      DoEvents
    Loop
    CadInputQueue.SendCommand "CHOOSE NONE"
  
  Else
      CadInputQueue.SendCommand "CHOOSE NONE"
  End If

  
End Sub

Attribute VB_Name = "ViewConfiguration"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public ViewNumber As Integer
Public PercentTop As Double
Public PercentBottom As Double
Public PercentLeft As Double
Public PercentRight As Double

Attribute VB_Name = "frmExaggerateZ"
Attribute VB_Base = "0{0753028E-8266-4014-B0A1-404F9779EE64}{3179D6CD-6595-4AF0-BC0D-18859D419E61}"
Attribute VB_GlobalNameSpace = False
Attribute VB_Creatable = False
Attribute VB_PredeclaredId = True
Attribute VB_Exposed = False
Attribute VB_TemplateDerived = False
Attribute VB_Customizable = False

Public OriginalModel As ModelReference
Public TempModel As ModelReference

Private Sub UserForm_Activate()

  ' Set default exaggeration
  txtExaggeration.Text = "1"

End Sub

Private Sub UserForm_Terminate()

  ' Try to activate the original model
  If Not OriginalModel Is Nothing Then
    OriginalModel.Activate
  End If

  ' Try to remove the temporary model
  If Not TempModel Is Nothing Then
    If Not TempModel.IsActive Then
      ActiveDesignFile.Models.Delete TempModel
    End If
  End If

End Sub

Private Sub cmdExaggerate_Click()

  If Not TempModel Is Nothing And txtExaggeration.Text <> "" Then
    Dim dblExaggeration As Double
    On Error Resume Next
    dblExaggeration = txtExaggeration.Text
    On Error GoTo 0
    If dblExaggeration <= 0 Then
      MsgBox "Invalid Exaggeration value"
      Exit Sub
    End If
    
    If ActiveModelReference.Attachments.Count > 0 Then
      If ActiveModelReference.Attachments(1).LogicalName = "Temp3DVis" Then
        ' Good attachment so use it
        Dim GetDP As New GetDPLocation
        GetDP.ZScale = dblExaggeration
        GetDP.AttInx = 1
        CommandState.EnableAccuSnap
        CommandState.StartPrimitive GetDP
      Else
        ' Bad attachment
        MsgBox ("Could not obtain attachment")
        Exit Sub
      End If
    Else
      ' Bad attachment
      MsgBox ("Could not obtain attachment")
      Exit Sub
    End If
  Else
    ' Bad attachment
    MsgBox ("Please select an attachment")
    Exit Sub
  End If

End Sub

Private Sub cmdRemoveExaggeration_Click()

  If ActiveModelReference.Attachments.Count > 0 Then
    If ActiveModelReference.Attachments(1).LogicalName = "Temp3DVis" Then
      ' Good attachment so use it
      Dim trnsCurr As Transform3d
      trnsCurr = ActiveModelReference.Attachments(1).GetMasterToReferenceTransform
      ActiveModelReference.Attachments(1).Transform trnsCurr, True
      ActiveModelReference.Attachments(1).Rewrite
      CursorInformation.CurrentView.Redraw
    Else
      ' Bad attachment
      MsgBox ("Could not obtain attachment")
      Exit Sub
    End If
  Else
    ' Bad attachment
    MsgBox ("Could not obtain attachment")
    Exit Sub
  End If

End Sub
