Attribute VB_Name = "modSnappableToggle"
Option Explicit

Public FSOActive As New FileSystemObject

Public Sub SnappableToggle()

  '' Get the list of levels from the file
  Dim LevelList As Collection
  Set LevelList = GetLevelList

  If LevelList Is Nothing Then
    ' Already told user so just quit
    Exit Sub
  End If

  ' Set up the scan
  Dim scanCrit As New ElementScanCriteria
  scanCrit.ExcludeAllLevels
  scanCrit.ExcludeAllTypes
  
  ' Scan only for lines
  scanCrit.IncludeType msdElementTypeLine
  
  ' Scan only for levels from the file
  Dim strLevelNameCurr As Variant
  Dim lvlCurr As Level
  Dim strMissingLevelList As String
  For Each strLevelNameCurr In LevelList
    Set lvlCurr = ActiveDesignFile.Levels.Find(strLevelNameCurr)
    If Not lvlCurr Is Nothing Then
      ' Got this level so include it
      scanCrit.IncludeLevel lvlCurr
    Else
      If strMissingLevelList = "" Then
        strMissingLevelList = strLevelNameCurr
      Else
        strMissingLevelList = strMissingLevelList & ", " & strLevelNameCurr
      End If
    End If
  Next strLevelNameCurr
  
  ' Let user know if levels were missing
  If strMissingLevelList <> "" Then
    Dim dlgResult As VbMsgBoxResult
    dlgResult = MsgBox("Some levels were not found (" & strMissingLevelList & "), do you want to continue?", vbYesNo, "Missing Levels")
    If dlgResult = vbNo Then
      Exit Sub
    End If
  End If

  ' Scan criteria is set so get elements
  Dim elmEnum As ElementEnumerator
  Set elmEnum = ActiveModelReference.Scan(scanCrit)

  ' Process each element
  Dim intElmCnt As Integer
  Do While elmEnum.MoveNext
    If elmEnum.Current.IsSnappable = True Then
      intElmCnt = intElmCnt + 1
      elmEnum.Current.IsSnappable = False
      elmEnum.Current.Rewrite
    Else
      intElmCnt = intElmCnt + 1
      elmEnum.Current.IsSnappable = True
      elmEnum.Current.Rewrite
    End If
  Loop

  ' Inform the user
  ' MessageCenter.AddMessage Str(intElmCnt) & " Elements Modified to be 'Not Snappable'"
  MessageCenter.AddMessage Str(intElmCnt) & " Elements Modified"

End Sub

'Public Sub LevelsOff()
'
'  ' Get the list of levels from the file
'  Dim LevelList As Collection
'  Set LevelList = GetLevelList
'
'  If LevelList Is Nothing Then
'    ' Already told user so just quit
'    Exit Sub
'  End If
'
'  Dim strLevelNameCurr As Variant
'  Dim lvlCurr As Level
'  Dim vwCurr As View
'  Dim strCmd As String
'  Set vwCurr = CommandState.LastView
'  For Each strLevelNameCurr In LevelList
'    ' Send a keyin
'    strCmd = "OF=""" & strLevelNameCurr & """;SELVIEW " & vwCurr.Index
'    CadInputQueue.SendKeyin strCmd
''    Set lvlCurr = ActiveDesignFile.Levels.Find(strLevelNameCurr)
''    If Not lvlCurr Is Nothing Then
''      ' Got this level so turn it off
''      lvlCurr.IsDisplayedInView(vwCurr) = False
''
''    End If
'  Next strLevelNameCurr
'  vwCurr.Redraw
'
'End Sub
'
'Public Sub LevelsOn()
'
'  ' Get the list of levels from the file
'  Dim LevelList As Collection
'  Set LevelList = GetLevelList
'
'  If LevelList Is Nothing Then
'    ' Already told user so just quit
'    Exit Sub
'  End If
'
'  Dim strLevelNameCurr As Variant
''  Dim lvlCurr As Level
'  Dim vwCurr As View
'  Set vwCurr = CommandState.LastView
'  Dim strCmd As String
'  For Each strLevelNameCurr In LevelList
'    ' Send a keyin
'    strCmd = "ON=""" & strLevelNameCurr & """;SELVIEW " & vwCurr.Index
'    CadInputQueue.SendKeyin strCmd
''    Set lvlCurr = ActiveDesignFile.Levels.Find(strLevelNameCurr)
''    If Not lvlCurr Is Nothing Then
''      ' Got this level so turn it on
''      lvlCurr.IsDisplayedInView(vwCurr) = True
''    End If
'  Next strLevelNameCurr
'  vwCurr.Redraw
'
'End Sub

Public Sub LevelsToggle()

  ' Get the list of levels from the file
  Dim LevelList As Collection
  Set LevelList = GetLevelList

  If LevelList Is Nothing Then
    ' Already told user so just quit
    Exit Sub
  End If

  Dim strLevelNameCurr As Variant
  Dim lvlCurr As Level
  Dim vwCurr As View
  Dim strCmd As String
  Set vwCurr = CommandState.LastView
  For Each strLevelNameCurr In LevelList
    Set lvlCurr = ActiveModelReference.Levels.Find(strLevelNameCurr)
    If Not lvlCurr Is Nothing Then
      ' Got this level so set display depending on current display status
      If Not lvlCurr.IsFrozen Then
        If lvlCurr.IsEffectivelyDisplayedInView(vwCurr) Then
          lvlCurr.IsDisplayedInView(vwCurr) = False
        Else
          ' Make sure global display is on
          lvlCurr.IsDisplayed = True
          lvlCurr.IsDisplayedInView(vwCurr) = True
        End If
      End If
    End If
  Next strLevelNameCurr
  vwCurr.Redraw

End Sub

Private Function GetLevelList() As Collection

  Dim strLevelListFile As String
  Dim strAppPath As String
  
  strLevelListFile = GetFilePath
 
  If Not FSOActive.FileExists(strLevelListFile) Then
    MsgBox "Level List File not found (" & strLevelListFile & "), cannot continue"
    Exit Function
  End If

  ' Try to get level list
  Dim LevelList As New Collection
  Dim strLineIn As String
  Open strLevelListFile For Input As #1
  Do While Not EOF(1)
    Line Input #1, strLineIn
    strLineIn = Trim(strLineIn)
    If Not strLineIn Like "[#]*" And strLineIn <> "" Then
      ' Not a comment line or blank line so assume it's a level name
      LevelList.Add strLineIn
    End If
  Loop
  Close #1

  If LevelList.Count = 0 Then
    MsgBox "No levels loaded from level list file, cannot continue"
    Exit Function
  End If

  ' Got something so return it
  Set GetLevelList = LevelList

End Function

Private Function GetFilePath() As String

    
  ' get the path from the config variable if defined and if the file exists
  If ActiveWorkspace.IsConfigurationVariableDefined("CIVIL_SNAPPABLETOGGLE_LEVELS_FILE") Then
    Dim configVariable As String
    GetFilePath = ActiveWorkspace.ConfigurationVariableValue("CIVIL_SNAPPABLETOGGLE_LEVELS_FILE")
    If FSOActive.FileExists(GetFilePath) Then
        Exit Function
    End If
  End If

  Dim oVBE As VBIDE.VBE
  Dim strPath As String

  ' Get the path where this project was run from for the location of the layout file
  Set oVBE = VBE
  strPath = oVBE.ActiveVBProject.FileName
  ' Extract just the path
  If strPath <> "" Then
    GetFilePath = FSOActive.GetParentFolderName(strPath) & "\SnappableToggle_Levels.txt"
  Else
    GetFilePath = "C:\SnappableToggle_Levels.txt"""
  End If

End Function
