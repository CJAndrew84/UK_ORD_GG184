Attribute VB_Name = "frmSortSections"
Attribute VB_Base = "0{DCFD4799-AA08-4844-A437-EF14BDCE864A}{70C78B7E-27DB-4F63-ACCD-50D562A5E38A}"
Attribute VB_GlobalNameSpace = False
Attribute VB_Creatable = False
Attribute VB_PredeclaredId = True
Attribute VB_Exposed = False
Attribute VB_TemplateDerived = False
Attribute VB_Customizable = False
Private Sub CmdOK_Click()

 Dim MAXROW As Integer
 Dim DELTAX As Double
 Dim DELTAY As Double
 Dim att As Attachment
 Dim i As Integer
 Dim rowIndex, colIndex As Integer

' init
CadInputQueue.SendCommand "NULL"
rowIndex = 0
colIndex = 0

MAXROW = txtMAXROWS.Value
DELTAX = txtCOLSPACE.Value
DELTAY = txtROWSPACE.Value

For i = 1 To ActiveModelReference.Attachments.Count
    Set att = ActiveModelReference.Attachments(i)
    
    ' shift location
    att.Redraw msdDrawingModeErase
    SetOriginTo att, Point3dFromXY(colIndex * DELTAX, rowIndex * DELTAY)

    ' update row/column
    rowIndex = rowIndex + 1
    If (rowIndex = MAXROW) Then
        rowIndex = 0
        colIndex = colIndex + 1
    End If
    
    ' update attachment
    att.Rewrite
    att.Redraw
Next i

CommandState.StartDefaultCommand

Unload Me

End Sub

Private Sub Label1_Click()

End Sub

Private Sub Label3_Click()

End Sub

Private Sub txtMAXROWS_Change()

End Sub

Private Sub UserForm_Activate()
    
    ' Set default exaggeration
    txtMAXROWS.Text = "10"
    txtROWSPACE.Text = "0.5"
    txtCOLSPACE.Text = "0.5"

End Sub

Sub SetOriginTo(att As Attachment, destination As Point3d)

Dim distance As Point3d

' move attachment origin
distance = Point3dSubtract(destination, att.MasterOrigin)
att.Move distance, True

End Sub

Attribute VB_Name = "modArrangeXS"
Option Explicit

Sub ArrangeCrossSections()

Dim att As Attachment
Dim i As Integer
Dim rowIndex, colIndex As Integer

' init
CadInputQueue.SendCommand "NULL"
rowIndex = 0
colIndex = 0

' user ok
If (MsgBox("Arrange cross sections", vbQuestion Or vbYesNo) = vbNo) Then
    Exit Sub
End If

frmSortSections.Show vbModal

End Sub

Sub SetOriginTo(att As Attachment, destination As Point3d)

Dim distance As Point3d

' move attachment origin
distance = Point3dSubtract(destination, att.MasterOrigin)
att.Move distance, True

End Sub
