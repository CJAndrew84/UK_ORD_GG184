Attribute VB_Name = "UserForm1"
Attribute VB_Base = "0{1E1CC2F3-5E15-41E9-97D2-4898FE614807}{D8F22C19-A539-4848-84CB-F914F8CD9C73}"
Attribute VB_GlobalNameSpace = False
Attribute VB_Creatable = False
Attribute VB_PredeclaredId = True
Attribute VB_Exposed = False
Attribute VB_TemplateDerived = False
Attribute VB_Customizable = False
Private Sub ListBox1_Click()
Property GetAlignments() As List(Of String)
        Get #1, , GetAlignments
            Dim alignmentNames As List(Of String) = New List(Of String)

            'Checking for Active SDK connection and Alignment nullification
            If SDKCon.GetActive() Is Nothing Or SDKCon.GetActive().Alignments Is Nothing Then
                alignmentNames.Add ("None")
            Else
                For Each alignment As SDK.Alignment In SDKCon.GetActive().Alignments
                    If Not String.IsNullOrEmpty(alignment.Name) Then
                        alignmentNames.Add (Alignment.Name)
                    End If
                Next
            End If
            Return alignmentNames
        End Get
    End Property
End Sub
