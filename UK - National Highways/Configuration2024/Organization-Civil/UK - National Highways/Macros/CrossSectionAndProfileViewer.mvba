Attribute VB_Name = "frmMain"
Attribute VB_Base = "0{D70ADCC9-8AD1-47C7-B0CE-376C72E2FD69}{DBAEA635-CDF8-4E5E-967B-6F6909365012}"
Attribute VB_GlobalNameSpace = False
Attribute VB_Creatable = False
Attribute VB_PredeclaredId = True
Attribute VB_Exposed = False
Attribute VB_TemplateDerived = False
Attribute VB_Customizable = False
Private Declare PtrSafe Sub Sleep Lib "kernel32" (ByVal dwMilliseconds As Long)

Private Sub cbZoom_Change()

    ' Apply zoom ratio:
    Set oView = ActiveDesignFile.Views(1)
    If cbZoom.Value = "1" Then
        oView.Fit (True)
    Else
        oView.Fit (True)
        oView.Zoom (1 / cbZoom.Value)
    End If
    oView.Redraw
End Sub

Private Sub imgForwards_Click()

    imgForwards.SpecialEffect = fmSpecialEffectSunken
    Call ViewNext("Forward")
End Sub

Private Sub imgBackwards_Click()

    imgBackwards.SpecialEffect = fmSpecialEffectSunken
    Call ViewNext("Backward")
End Sub

Private Sub imgPlay_Click()

    imgPlay.SpecialEffect = fmSpecialEffectSunken
    Call ViewNext("Play")
End Sub

Private Sub imgStart_Click()

    imgStart.SpecialEffect = fmSpecialEffectSunken
    Call ViewNext("Start")
End Sub

Private Sub imgEnd_Click()

    imgEnd.SpecialEffect = fmSpecialEffectSunken
    Call ViewNext("End")
End Sub

Private Sub imgHide_Click()
    
    Me.Height = 66
    imgHide.Visible = False
    imgShow.Visible = True
End Sub

Private Sub imgshow_Click()
    
    Me.Height = 175
    imgHide.Visible = True
    imgShow.Visible = False
End Sub

Private Sub imgPlay_MouseMove(ByVal Button As _
     Integer, ByVal Shift As Integer, ByVal X As _
     Single, ByVal Y As Single)

    imgPlay.SpecialEffect = fmSpecialEffectRaised
End Sub

Private Sub imgForwards_MouseMove(ByVal Button As _
     Integer, ByVal Shift As Integer, ByVal X As _
     Single, ByVal Y As Single)

    imgForwards.SpecialEffect = fmSpecialEffectRaised
End Sub

Private Sub imgBackwards_MouseMove(ByVal Button As _
     Integer, ByVal Shift As Integer, ByVal X As _
     Single, ByVal Y As Single)

    imgBackwards.SpecialEffect = fmSpecialEffectRaised
End Sub

Private Sub imgStart_MouseMove(ByVal Button As _
     Integer, ByVal Shift As Integer, ByVal X As _
     Single, ByVal Y As Single)

    imgStart.SpecialEffect = fmSpecialEffectRaised
End Sub

Private Sub imgEnd_MouseMove(ByVal Button As _
     Integer, ByVal Shift As Integer, ByVal X As _
     Single, ByVal Y As Single)

    imgEnd.SpecialEffect = fmSpecialEffectRaised
End Sub

Private Sub imgHide_MouseMove(ByVal Button As _
     Integer, ByVal Shift As Integer, ByVal X As _
     Single, ByVal Y As Single)

    imgHide.SpecialEffect = fmSpecialEffectRaised
End Sub

Private Sub imgShow_MouseMove(ByVal Button As _
     Integer, ByVal Shift As Integer, ByVal X As _
     Single, ByVal Y As Single)

    imgShow.SpecialEffect = fmSpecialEffectRaised
End Sub

Private Sub obCrossSections_Click()

    Me.lblProfileKey.Visible = False
    Me.tbProfileKey.Visible = False
End Sub

Private Sub obProfiles_Click()

    Me.lblProfileKey.Visible = True
    Me.tbProfileKey.Visible = True
End Sub

Private Sub UserForm_MouseMove(ByVal Button As _
     Integer, ByVal Shift As Integer, ByVal X As _
     Single, ByVal Y As Single)
     
    imgForwards.SpecialEffect = fmSpecialEffectFlat
    imgBackwards.SpecialEffect = fmSpecialEffectFlat
    imgStart.SpecialEffect = fmSpecialEffectFlat
    imgEnd.SpecialEffect = fmSpecialEffectFlat
    imgHide.SpecialEffect = fmSpecialEffectFlat
    imgShow.SpecialEffect = fmSpecialEffectFlat
    imgPlay.SpecialEffect = fmSpecialEffectFlat
End Sub

Private Sub UserForm_QueryClose(Cancel As Integer, CloseMode As Integer)

    Dim IniFile As String
    
    On Error GoTo END_SUBROUTINE
    ' Save the user's settings:
    IniFile = ActiveWorkspace.ConfigurationVariableValue("MS_VBANEWPROJECTDIRECTORY") + "Cross Section and Profile Viewer.ini"
    Open IniFile For Output As #1
    Write #1, Me.obCrossSections.Value
    Write #1, Me.obProfiles.Value
    Write #1, Me.obDrawings.Value
    Write #1, Me.obSheets.Value
    Write #1, Me.tbProfileKey.Value
    Write #1, Me.cbZoom.Value
    Write #1, Me.Top
    Write #1, Me.Left
    Close #1
END_SUBROUTINE:
End Sub

Sub ViewNext(Mode As String)

    Dim oModel As ModelReference
    Dim Count As Integer
    Dim GotMultipleModels As Boolean
    Dim Models() As String
    Dim oView As View
    Dim i As Integer
    Dim SearchString As String
    Dim FolderPath As String
    Dim StrFile As String
    Dim LastModelReached As Boolean

    If obProfiles.Value = True Then
        If tbProfileKey.Value = "" Then
            MsgBox "Please specify a Profile Search String. This should be the common part of profile model names, such as ""PP"".", vbOKOnly Or vbExclamation, "No Profile Key String Specified"
            Exit Sub
        Else
            SearchString = tbProfileKey.Value
        End If
    Else
        SearchString = "+"
    End If
    
    ' Check to see if models are all in one file.
    For Each oModel In ActiveDesignFile.Models
        If InStr(oModel.Name, SearchString) <> 0 Then
            Count = Count + 1
            If Count > 1 Then
                GotMultipleModels = True
                Exit For
            End If
        End If
    Next
    
    If GotMultipleModels = True Then
        For Each oModel In ActiveDesignFile.Models
            If InStr(oModel.Name, SearchString) <> 0 Then
                If obDrawings.Value = True And oModel.Type = msdModelTypeDrawing Then
                    If Not Not Models Then ' the array is initialized.
                        ReDim Preserve Models(UBound(Models) + 1)
                    Else
                        ReDim Models(0)
                    End If
                    Models(UBound(Models)) = oModel.Name
                ElseIf obSheets.Value = True And oModel.Type = msdModelTypeSheet Then
                    If Not Not Models Then ' the array is initialized.
                        ReDim Preserve Models(UBound(Models) + 1)
                    Else
                        ReDim Models(0)
                    End If
                    Models(UBound(Models)) = oModel.Name
                End If
            End If
        Next
        
        Select Case Mode
            Case "Start"
                Set oModel = ActiveDesignFile.Models.Item(Models(LBound(Models)))
                oModel.Activate
            Case "Backward"
                For i = LBound(Models) To UBound(Models)
                    If Models(i) = ActiveModelReference.Name Then
                        Exit For
                    End If
                Next
                If i <> LBound(Models) Then
                    Set oModel = ActiveDesignFile.Models.Item(Models(i - 1))
                    oModel.Activate
                Else
                    imgBackwards.SpecialEffect = fmSpecialEffectFlat
                    MsgBox "First item reached", vbInformation Or vbOKOnly, "Beginning Reached"
                End If
            Case "Play"
                LastModelReached = False
                Do While LastModelReached = False
                    Call Forward(Models, LastModelReached)
                    
                    ' Apply zoom ratio:
                    Set oView = ActiveDesignFile.Views(1)
                    If cbZoom.Value = "1" Then
                        oView.Fit (True)
                    Else
                        oView.Fit (True)
                        oView.Zoom (1 / cbZoom.Value)
                    End If
                    oView.Redraw
                    
                    Sleep 1000
                Loop
            Case "Forward"
                Call Forward(Models, LastModelReached)
            Case "End"
                Set oModel = ActiveDesignFile.Models.Item(Models(UBound(Models)))
                oModel.Activate
        End Select
        
        ' Apply zoom ratio:
        Set oView = ActiveDesignFile.Views(1)
        If cbZoom.Value = "1" Then
            oView.Fit (True)
        Else
            oView.Fit (True)
            oView.Zoom (1 / cbZoom.Value)
        End If
        oView.Redraw
    End If
End Sub

Sub Forward(Models() As String, LastModelReached As Boolean)

    Dim i As Integer

    For i = LBound(Models) To UBound(Models)
        If Models(i) = ActiveModelReference.Name Then
            Exit For
        End If
    Next
    If i + 1 <= UBound(Models) Then
        Set oModel = ActiveDesignFile.Models.Item(Models(i + 1))
        oModel.Activate
        If i + 1 = UBound(Models) Then LastModelReached = True
    Else
        LastModelReached = True
        imgForwards.SpecialEffect = fmSpecialEffectFlat
        MsgBox "Last item reached", vbInformation Or vbOKOnly, "End Reached"
    End If
End Sub

Attribute VB_Name = "modStartCSPV"
' Version 1.1
' 6/30/2020
    ' Version 1.1
        ' - Added control tip text to navigation controls.
        ' - Added Play feature.
        ' - Added Zoom Ratio.
        ' - Removed Fit View (now Zoom Ratio = 1).
        ' - Default to sheet or drawing base on active model type.
        ' - Hide Plan and Profile Search String when processing cross sections.
        ' - Fixed a bug when pressing Next after switching between cross sections and plan and profiles caused a crash.
' Developed by Bentley Systems

Option Explicit

Sub Main()

    Dim IniFile As String
    Dim Val
    
    ' Populate cbZoom values:
    If frmMain.cbZoom.ListCount = 0 Then
        frmMain.cbZoom.AddItem "1"
        frmMain.cbZoom.AddItem "1.25"
        frmMain.cbZoom.AddItem "1.5"
        frmMain.cbZoom.AddItem "1.75"
        frmMain.cbZoom.AddItem "2"
    End If

    ' Read the user's settings:
    IniFile = ActiveWorkspace.ConfigurationVariableValue("MS_VBANEWPROJECTDIRECTORY") + "Cross Section and Profile Viewer.ini"
    If Dir(IniFile) <> "" Then
        Open IniFile For Input As #1
        Input #1, Val
        frmMain.obCrossSections.Value = Val
        Input #1, Val
        frmMain.obProfiles.Value = Val
        Input #1, Val
        frmMain.obDrawings.Value = Val
        Input #1, Val
        frmMain.obSheets.Value = Val
        Input #1, Val
        frmMain.tbProfileKey.Value = Val
        Input #1, Val
        frmMain.cbZoom.Value = Val
        Input #1, Val
        frmMain.Top = Val
        Input #1, Val
        frmMain.Left = Val
        Close #1
    End If

    ' Default Model Type to active model type:
    If ActiveModelReference.Type = msdModelTypeDrawing Then
        frmMain.obDrawings.Value = True
    ElseIf ActiveModelReference.Type = msdModelTypeSheet Then
        frmMain.obSheets.Value = True
    End If
    
    ' Only show Profile Search String if Plan & Profiles is selected:
    If frmMain.obProfiles.Value = True Then
        frmMain.lblProfileKey.Visible = True
        frmMain.tbProfileKey.Visible = True
    Else
        frmMain.lblProfileKey.Visible = False
        frmMain.tbProfileKey.Visible = False
    End If
    
    frmMain.Show (False)
End Sub
