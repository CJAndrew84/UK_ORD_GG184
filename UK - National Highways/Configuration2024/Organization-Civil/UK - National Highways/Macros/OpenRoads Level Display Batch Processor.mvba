Attribute VB_Name = "FormMain"
Attribute VB_Base = "0{A52723F2-9F17-47DF-BE76-AEA3DA226A6F}{269FD64A-6AF3-445A-A4C8-732E41DF69A7}"
Attribute VB_GlobalNameSpace = False
Attribute VB_Creatable = False
Attribute VB_PredeclaredId = True
Attribute VB_Exposed = False
Attribute VB_TemplateDerived = False
Attribute VB_Customizable = False
Option Explicit

Private fsoActive As New FileSystemObject

Private levelInfoListActive As Collection
Private levelInfoList0 As Collection
Private levelInfoList1 As Collection
Private levelInfoList2 As Collection
Private levelInfoList3 As Collection

Private displayCmds As Collection
    
Private oView As View
    
Private Sub cbActiveFile_Click()

End Sub

Private Sub CheckBox2_Click()

End Sub

Private Sub CmdOK_Click()
    
    'Me.Hide
    CadInputQueue.SendCommand "filedesign"
    
    Set oView = ActiveDesignFile.Views.Item(1)
    
    Set displayCmds = New Collection

    ' *********************************************
    ' **** COLLECT LEVELS AND HOW THEY'RE USED ****
    ' *********************************************
    ' Active model
    Dim levelInfo As clsDisplayInfo
    Dim oLevel As Level
    Set levelInfoListActive = New Collection
    For Each oLevel In ActiveModelReference.Levels
     If Not oLevel.IsFromLevelLibrary And oLevel.IsInUse Then
        Set levelInfo = New clsDisplayInfo
        levelInfo.LevelName = oLevel.Name
        levelInfo.IsDisplayed = oLevel.IsDisplayedInView(oView)
        levelInfoListActive.Add levelInfo
      End If
    Next oLevel
    
    Set levelInfoList0 = New Collection
    Set levelInfoList1 = New Collection
    Set levelInfoList2 = New Collection
    Set levelInfoList3 = New Collection
    
    Dim oAttachment_NestDepth1 As attachment
    Dim oAttachment_NestDepth2 As attachment
    Dim oAttachment_NestDepth3 As attachment
    If ActiveModelReference.Attachments.Count > 0 Then
        Dim firstAttachment As attachment
        Set firstAttachment = ActiveModelReference.Attachments(1)
        GetLevelsForAttachment firstAttachment, oView, levelInfoList0

        If cbToggleRefs = True Then
          If firstAttachment.DisplayFlag = True Then
            displayCmds.Add "reference display on " & firstAttachment.AttachName
          Else
            displayCmds.Add "reference display off " & firstAttachment.AttachName
          End If
        End If

        For Each oAttachment_NestDepth1 In firstAttachment.Attachments
            GetLevelsForAttachment oAttachment_NestDepth1, oView, levelInfoList1

            If cbToggleRefs = True Then
                If oAttachment_NestDepth1.DisplayFlag = True Then
                  displayCmds.Add "reference display on " & firstAttachment.AttachName & "->" & oAttachment_NestDepth1.AttachName
                Else
                  displayCmds.Add "reference display off " & firstAttachment.AttachName & "->" & oAttachment_NestDepth1.AttachName
                End If
            End If

            For Each oAttachment_NestDepth2 In oAttachment_NestDepth1.Attachments
                GetLevelsForAttachment oAttachment_NestDepth2, oView, levelInfoList2

                If cbToggleRefs = True Then
                    If oAttachment_NestDepth2.DisplayFlag = True Then
                      displayCmds.Add "reference display on " & firstAttachment.AttachName & "->" & oAttachment_NestDepth1.AttachName & "->" & oAttachment_NestDepth2.AttachName
                    Else
                      displayCmds.Add "reference display off " & firstAttachment.AttachName & "->" & oAttachment_NestDepth1.AttachName & "->" & oAttachment_NestDepth2.AttachName
                    End If
                End If

                For Each oAttachment_NestDepth3 In oAttachment_NestDepth2.Attachments
                    GetLevelsForAttachment oAttachment_NestDepth3, oView, levelInfoList3

                    If cbToggleRefs = True Then
                        If oAttachment_NestDepth3.DisplayFlag = True Then
                          displayCmds.Add "reference display on " & firstAttachment.AttachName & "->" & oAttachment_NestDepth1.AttachName & "->" & oAttachment_NestDepth2.AttachName & "->" & oAttachment_NestDepth3.AttachName
                        Else
                          displayCmds.Add "reference display off " & firstAttachment.AttachName & "->" & oAttachment_NestDepth1.AttachName & "->" & oAttachment_NestDepth2.AttachName & "->" & oAttachment_NestDepth3.AttachName
                        End If
                    End If

                Next
            Next
        Next
    End If
    
    ' Compose keyin commands
    Dim strOnLevels As String
    Dim strOffLevels As String
    For Each levelInfo In levelInfoListActive
      If levelInfo.IsDisplayed Then
        If Len(strOnLevels) > 0 Then
          strOnLevels = strOnLevels & ","
        End If
        strOnLevels = strOnLevels & Chr(34) & levelInfo.LevelName & Chr(34)
        If Len(strOnLevels) > 700 Then
          displayCmds.Add "set levels on " & strOnLevels & "; selview 1"
          strOnLevels = ""
        End If
      Else
        If Len(strOffLevels) > 0 Then
          strOffLevels = strOffLevels & ","
        End If
        strOffLevels = strOffLevels & Chr(34) & levelInfo.LevelName & Chr(34)
        If Len(strOffLevels) > 700 Then
          displayCmds.Add "set levels off " & strOffLevels & "; selview 1"
          strOffLevels = ""
        End If
      End If
    Next levelInfo

    If Len(strOnLevels) > 0 Then
      displayCmds.Add "set levels on " & strOnLevels & "; selview 1"
    End If
    If Len(strOffLevels) > 0 Then
      displayCmds.Add "set levels off " & strOffLevels & "; selview 1"
    End If

    strOnLevels = ""
    strOffLevels = ""
    For Each levelInfo In levelInfoList0
      If levelInfo.IsDisplayed Then
        If Len(strOnLevels) > 0 Then
          strOnLevels = strOnLevels & ","
        End If
        strOnLevels = strOnLevels & Chr(34) & levelInfo.LevelName & Chr(34)
        If Len(strOnLevels) > 700 Then
          displayCmds.Add "reference levels on " & strOnLevels & " *.*; selview 1"
          strOnLevels = ""
        End If
      Else
        If Len(strOffLevels) > 0 Then
          strOffLevels = strOffLevels & ","
        End If
        strOffLevels = strOffLevels & Chr(34) & levelInfo.LevelName & Chr(34)
        If Len(strOffLevels) > 700 Then
          displayCmds.Add "reference levels off " & strOffLevels & " *.*; selview 1"
          strOffLevels = ""
        End If
      End If
    Next levelInfo

    If Len(strOnLevels) > 0 Then
      displayCmds.Add "reference levels on " & strOnLevels & " *.*; selview 1"
    End If
    If Len(strOffLevels) > 0 Then
      displayCmds.Add "reference levels off " & strOffLevels & " *.*; selview 1"
    End If

    strOnLevels = ""
    strOffLevels = ""
    For Each levelInfo In levelInfoList1
      If levelInfo.IsDisplayed Then
        If Len(strOnLevels) > 0 Then
          strOnLevels = strOnLevels & ","
        End If
        strOnLevels = strOnLevels & Chr(34) & levelInfo.LevelName & Chr(34)
        If Len(strOnLevels) > 700 Then
          displayCmds.Add "reference levels on " & strOnLevels & " *.*->*.*; selview 1"
          strOnLevels = ""
        End If
      Else
        If Len(strOffLevels) > 0 Then
          strOffLevels = strOffLevels & ","
        End If
        strOffLevels = strOffLevels & Chr(34) & levelInfo.LevelName & Chr(34)
        If Len(strOffLevels) > 700 Then
          displayCmds.Add "reference levels off " & strOffLevels & " *.*->*.*; selview 1"
          strOffLevels = ""
        End If
      End If
    Next levelInfo

    If Len(strOnLevels) > 0 Then
      displayCmds.Add "reference levels on " & strOnLevels & " *.*->*.*; selview 1"
    End If
    If Len(strOffLevels) > 0 Then
      displayCmds.Add "reference levels off " & strOffLevels & " *.*->*.*; selview 1"
    End If

    strOnLevels = ""
    strOffLevels = ""
    For Each levelInfo In levelInfoList2
      If levelInfo.IsDisplayed Then
        If Len(strOnLevels) > 0 Then
          strOnLevels = strOnLevels & ","
        End If
        strOnLevels = strOnLevels & Chr(34) & levelInfo.LevelName & Chr(34)
        If Len(strOnLevels) > 700 Then
          displayCmds.Add "reference levels on " & strOnLevels & " *.*->*.*->*.*; selview 1"
          strOnLevels = ""
        End If
      Else
        If Len(strOffLevels) > 0 Then
          strOffLevels = strOffLevels & ","
        End If
        strOffLevels = strOffLevels & Chr(34) & levelInfo.LevelName & Chr(34)
        If Len(strOffLevels) > 700 Then
          displayCmds.Add "reference levels off " & strOffLevels & " *.*->*.*->*.*; selview 1"
          strOffLevels = ""
        End If
      End If
    Next levelInfo

    If Len(strOnLevels) > 0 Then
      displayCmds.Add "reference levels on " & strOnLevels & " *.*->*.*->*.*; selview 1"
    End If
    If Len(strOffLevels) > 0 Then
      displayCmds.Add "reference levels off " & strOffLevels & " *.*->*.*->*.*; selview 1"
    End If

    ' Only process like models
    Dim SourceModelType As Long
    SourceModelType = ActiveModelReference.Type

    ' Process active file?
    If cbActiveFile.Value = True Then
      ProcessFile ActiveDesignFile.FullName, SourceModelType
    End If
    
    Dim i As Long
    For i = 0 To lbFiles.ListCount - 1
        If lbFiles.Selected(i) = True Then
            ProcessFile lbFiles.List(i), SourceModelType
        End If
    Next i
    
    CommandState.StartDefaultCommand

End Sub

Private Sub ProcessFile(dgnFileName As String, SourceModelType As Long)

    Dim oAttachment_NestDepth0 As attachment
    Dim oAttachment_NestDepth1 As attachment
    Dim oAttachment_NestDepth2 As attachment
    Dim oAttachment_NestDepth3 As attachment
    Dim oModel As ModelReference
    Dim l As Long
    Dim KeyInStr As String
    Dim i As Integer

    ' Escludi Drawing
    Dim TestoEscludi As String
    Dim TestoIncludi As String
    If ChkEscludi.Value Then
        TestoEscludi = TxtEscludi.Text
    Else
        TestoEscludi = "*"
    End If
    If ChkIncludi.Value Then
        TestoIncludi = TxtIncludi.Text
    Else
        TestoIncludi = "*"
    End If
    
    ' Open the file
    If Not fsoActive.FileExists(dgnFileName) Then
        MsgBox "File not found: " & dgnFileName, vbOKOnly, "Process File"
        Exit Sub
    End If
    
    If ActiveDesignFile.FullName <> dgnFileName Then
      OpenDesignFile dgnFileName
    End If

    For i = 1 To ActiveDesignFile.Models.Count
        Set oModel = ActiveDesignFile.Models(i)
        If oModel.Type = SourceModelType Then
            If (ChkEscludi.Value = False Or InStr(oModel.Name, TestoEscludi) = 0) And _
               (ChkIncludi.Value = False Or InStr(oModel.Name, TestoIncludi) <> 0) Then
                
                If ActiveModelReference.Name <> oModel.Name Then
                  oModel.Activate
                End If
                

                Dim cmdKeyin As Variant
                For Each cmdKeyin In displayCmds
                  CadInputQueue.SendKeyin cmdKeyin
                Next cmdKeyin
                
            End If
        End If

    Next ' Each model in the active design file
    
        oView.Redraw
'    ActiveDesignFile.RewriteLevels '.Levels.Rewrite
    CadInputQueue.SendCommand "filedesign"

End Sub

Private Sub GetLevelsForAttachment(attachment As attachment, oView As View, ByRef levelInfoList As Collection)

    Dim levelInfo As clsDisplayInfo
    Dim oLevel As Level
    For Each oLevel In attachment.Levels
        On Error Resume Next
        If oLevel.Name <> "" And Not (oLevel.IsFromLevelLibrary And Not oLevel.IsInUse) Then
            If Err = 0 Then
                Set levelInfo = New clsDisplayInfo
                levelInfo.LevelName = oLevel.Name
                levelInfo.IsDisplayed = oLevel.IsDisplayedInView(oView)
                levelInfoList.Add levelInfo
            End If
        End If
    Next oLevel

End Sub

Private Sub CmdCancel_Click()

    Me.Hide
End Sub

Private Sub cmdBrowseFile_Click()
    
    Dim dgnFile  As String
    Dim i As Integer
    Dim slashpos As Integer
    Dim FilePath As String
    Dim fileName As String
    Dim r As Integer
    
    dgnFile = ShowOpen("Open Design File", "OpenedUsingCommonDialog", "MicroStation Files (*.dgn)", "*.dgn", "D:\temp")
    If dgnFile <> "" Then
        i = 1
        Do While i < Len(dgnFile)
            If Mid$(dgnFile, i, 1) = "\" Then
                slashpos = i
            End If
            i = i + 1
        Loop
        
        Me.lbFiles.AddItem dgnFile
        For r = 0 To lbFiles.ListCount - 1
            If r = lbFiles.ListCount - 1 Then
                lbFiles.Selected(r) = True
            End If
        Next r
    End If
End Sub

Private Sub cmdBrowseFolder_Click()

    Dim Ret As String
    Dim FileFolder As String
    Dim fileName As String
    Dim r As Integer

    '~~> Specify your start folder here
    Ret = BrowseForFolder(Me.ComboDrive.Value)
    If Ret <> "" Then
        'Debug.Print Ret
        FileFolder = Ret + "\"
        
        ' Returns filename with specified extension. If more than one *.ini
        ' file exists, the first file found is returned.
        fileName = Dir(FileFolder + "*.dgn")
        Do While fileName <> ""
            Me.lbFiles.AddItem FileFolder + fileName
            For r = 0 To lbFiles.ListCount - 1
                If r = lbFiles.ListCount - 1 Then
                    lbFiles.Selected(r) = True
                End If
            Next r

            ' Call Dir again without arguments to return the next *.INI file in the
            ' same directory.
            fileName = Dir
        Loop
    End If
End Sub

Function BrowseForFolder(Optional OpenAt As Variant) As Variant
     'Function purpose:  To Browser for a user selected folder.
     'If the "OpenAt" path is provided, open the browser at that directory
     'NOTE:  If invalid, it will open at the Desktop level

    Dim ShellApp As Object

     'Create a file browser window at the default folder
    Set ShellApp = CreateObject("Shell.Application"). _
    BrowseForFolder(0, "Please choose a folder", 0, OpenAt)

     'Set the folder to that selected.  (On error in case cancelled)
    On Error Resume Next
    BrowseForFolder = ShellApp.self.Path
    'Debug.Print ShellApp.self.Path
    On Error GoTo 0

     'Destroy the Shell Application
    Set ShellApp = Nothing

     'Check for invalid or non-entries and send to the Invalid error
     'handler if found
     'Valid selections can begin L: (where L is a letter) or
     '\\ (as in \\servername\sharename.  All others are invalid
    Select Case Mid(BrowseForFolder, 2, 1)
    Case Is = ":"
        If Left(BrowseForFolder, 1) = ":" Then GoTo Invalid
    Case Is = "\"
        If Not Left(BrowseForFolder, 1) = "\" Then GoTo Invalid
    Case Else
        GoTo Invalid
    End Select

    Exit Function

Invalid:
     'If it was determined that the selection was invalid, set to False
    BrowseForFolder = False
End Function

Private Sub UserForm_QueryClose(Cancel As Integer, CloseMode As Integer)

    Dim IniFile As String

    ' Save the user's settings:
    IniFile = ActiveWorkspace.ConfigurationVariableValue("MS_VBANEWPROJECTDIRECTORY") + "OpenRoads Level Display Batch Processor.ini"
    Open IniFile For Output As #1
    Write #1, Me.cbActiveFile.Value
    Write #1, Me.ChkEscludi.Value
    Write #1, Me.TxtEscludi.Value
    Write #1, Me.ChkIncludi.Value
    Write #1, Me.TxtIncludi.Value
    Write #1, Me.cbToggleRefs.Value
    Write #1, Me.Top
    Write #1, Me.Left
    Close #1

End Sub

Attribute VB_Name = "clsDisplayInfo"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False

Public LevelName As String
Public IsDisplayed As Boolean

Attribute VB_Name = "modCommonDialogs"
Option Explicit
' --------------------------------------------------------------------
Private Declare PtrSafe Function GetOpenFileName Lib "comdlg32.dll" Alias "GetOpenFileNameA" ( _
    ByRef pOpenfilename As OPENFILENAME) As Long
Private Declare PtrSafe Function GetSaveFileName Lib "comdlg32.dll" Alias "GetSaveFileNameA" ( _
    ByRef pOpenfilename As OPENFILENAME) As Long

' ---------------------------------------------------------------------
'   Win32 API structure definition as user-defined type
' ---------------------------------------------------------------------
Private Type OPENFILENAME
  lStructSize As Long
  hwndOwner As LongPtr
  hInstance As LongPtr
  lpstrFilter As String
  lpstrCustomFilter As String
  nMaxCustFilter As Long
  nFilterIndex As Long
  lpstrFile As String
  nMaxFile As Long
  lpstrFileTitle As String
  nMaxFileTitle As Long
  lpstrInitialDir As String
  lpstrTitle As String
  flags As Long
  nFileOffset As Integer
  nFileExtension As Integer
  lpstrDefExt As String
  lCustData As Long
  lpfnHook As LongPtr
  lpTemplateName As String
End Type
' ---------------------------------------------------------------------
'   Win32 API constants
' ---------------------------------------------------------------------
Private Const BIF_NEWDIALOGSTYLE         As Long = &H40
Private Const BIF_RETURNONLYFSDIRS       As Long = 1
Private Const MAX_PATH                   As Long = 260
Private Const OFN_OVERWRITEPROMPT        As Long = &H2
Private Const OFN_FILEMUSTEXIST          As Long = &H1000
Private Const OFN_PATHMUSTEXIST          As Long = &H800
Private Const OFN_ALLOWMULTISELECT As Long = &H200
' ---------------------------------------------------------------------
'   ShowSave    Save As... common dialog
'   Arguments:  [in, String] dialog title,
'               [in, String] filter description, [optional]
'               [in, String] filter spec, [optional]
'               [in, String] default directory [optional]
'   Example call:
'   dgnFile = ShowSave ("Save Design File As...", "SavedUsingCommonDialog", _
'   "MicroStation Files (*.dgn)", "*.dgn", "V:\shared")
'   Returns:    full path of file to be saved
' ---------------------------------------------------------------------
Public Function ShowSave( _
    ByVal strDialogTitle As String, _
    ByVal strProposed As String, _
    Optional ByVal strFilterDescr As String = "All files (*.*)", _
    Optional ByVal strFilterSpec As String = "*.*", _
    Optional ByVal strDefaultDir As String = vbNullString) As String
    On Error Resume Next
    Dim strFilter                           As String, _
        strFileSelected                     As String, _
        proposed                            As String
    Dim OFName                              As OPENFILENAME
    strFilter = strFilterDescr + Chr$(0) + strFilterSpec + Chr$(0)

    proposed = strProposed & Chr$(0) & Space$(254 - Len(strProposed)) 'Create a buffer
    Const Period                            As String = "."
    With OFName
        .lStructSize = LenB(OFName) ' Set the structure size.  Note use of LenB() not Len()
        .hwndOwner = 0& ' Set the owner window
        .hInstance = 0& ' Set the application's instance
        .lpstrFilter = strFilter 'Set the filter
        .lpstrFile = proposed
        .lpstrDefExt = Mid$(strFilterSpec, 1 + InStr(strFilterSpec, Period))
        .nMaxFile = 255 ' Set the maximum number of chars
        .lpstrFileTitle = Space$(254) ' Create a buffer
        .nMaxFileTitle = 255 'Set the maximum number of chars
        If (vbNullString <> strDefaultDir) Then _
            .lpstrInitialDir = strDefaultDir 'Set the initial directory
        .lpstrTitle = strDialogTitle 'Set the dialog title
        .flags = OFN_OVERWRITEPROMPT 'no extra flags
    End With
    If GetSaveFileName(OFName) Then 'Show the 'Save File' dialog
        strFileSelected = Trim$(OFName.lpstrFile)
        If (InStr(strFileSelected, Chr(0)) > 0) Then
            strFileSelected = Left(strFileSelected, InStr(strFileSelected, Chr(0)) - 1)
        End If
        ShowSave = Trim(strFileSelected)
    Else
        ShowSave = ""
    End If
End Function
' ---------------------------------------------------------------------
'   ShowOpen    Open common dialog
'   Arguments:  [in, String] dialog title,
'               [in, String] proposed name, [optional]
'               [in, String] filter description, [optional]
'               [in, String] filter spec, [optional]
'               [in, String] default directory [optional]
'   Example call:
'   dgnFile = ShowOpen ("Open Design File", "MicroStation Files (*.dgn)", "*.dgn", "V:\shared")
'   Returns:    full path of file to be opened
' ---------------------------------------------------------------------
Public Function ShowOpen(ByVal title As String, _
        ByVal proposedName As String, _
        ByVal filterDescription As String, _
        ByVal filter As String, _
        ByVal initialDirectory As String) As String
    ShowOpen = vbNullString
    
    On Error Resume Next
    Dim strFilter                           As String, _
        strFileSelected                     As String, _
        proposed                            As String
    Dim OFName                              As OPENFILENAME
    strFilter = filterDescription + Chr$(0) + filter + Chr$(0)

    proposed = proposedName & Chr$(0) & Space$(254 - Len(proposed)) 'Create a buffer
    Const Period                            As String = "."
    With OFName
        .lStructSize = LenB(OFName) ' Set the structure size.  Note use of LenB() not Len()
        .hwndOwner = 0& ' Set the owner window
        .hInstance = 0& ' Set the application's instance
        .lpstrFilter = strFilter 'Set the filter
        .lpstrFile = proposed
        .lpstrDefExt = Mid$(filter, 1 + InStr(filter, Period))
        .nMaxFile = 255 ' Set the maximum number of chars
        .lpstrFileTitle = Space$(254) ' Create a buffer
        .nMaxFileTitle = 255 'Set the maximum number of chars
        If (vbNullString <> initialDirectory) Then _
            .lpstrInitialDir = initialDirectory 'Set the initial directory
        .lpstrTitle = title 'Set the dialog title
        .flags = OFN_FILEMUSTEXIST
    End With
    If GetOpenFileName(OFName) Then 'Show the 'Open File' dialog
        strFileSelected = Trim$(OFName.lpstrFile)
        If (InStr(strFileSelected, Chr(0)) > 0) Then
            strFileSelected = Left(strFileSelected, InStr(strFileSelected, Chr(0)) - 1)
        End If
        ShowOpen = Trim(strFileSelected)
    Else
        ShowOpen = vbNullString
    End If
End Function
' --------------------------------------------------------------------

Attribute VB_Name = "modLevelDisplay"

Sub Main()
    
    ' Version 1.5
    ' July 15, 2020
        ' Version 1.1:
            ' - Incorporated changes to only process levels that are actually used.
            ' - Added Exclude Model Name and Include Model Name fields
        ' Version 1.2:
            ' - Check the values of MS_LEVEL_DO_NOT_OVERRIDE_DESIGN_LEVELS_IN_SHEET and MS_REF_DEFAULTSETTINGS _
                configuration variables and alert users if they will interfere with the macro
            ' - Process design models
            ' - Added support for toggling reference attachment displays on and off
            ' - Save and restore user settings
            ' - Fixed warning image display resolution
    ' Developed by Bentley Systems.
    ' Intended for use on models created by OpenRoads Designer.
    
    Dim i As Integer
    Dim Value As Integer
    Dim ValStr As String
    Dim Val
    
    On Error Resume Next
    
    If ActiveModelReference.Type = msdModelTypeSheet Or ActiveModelReference.Type = msdModelTypeDrawing Then
        Value = ActiveWorkspace.ConfigurationVariableValue("MS_LEVEL_DO_NOT_OVERRIDE_DESIGN_LEVELS_IN_SHEET")
        If Value = 1 Then
            MsgBox "Configuration variable MS_LEVEL_DO_NOT_OVERRIDE_DESIGN_LEVELS_IN_SHEET is set to ""1."" Therefore, this macro will not work on drawing or sheet models.", _
                vbOKOnly Or vbExclamation, "Configuration Variable Warning"
            Exit Sub
        End If
    End If
    
    ValStr = ActiveWorkspace.ConfigurationVariableValue("MS_REF_DEFAULTSETTINGS")
    If InStr(UCase(ValStr), "NESTOVERRIDES=NEVER") <> 0 Then
        MsgBox "Configuration variable MS_REF_DEFAULTSETTINGS is set to ""nestoverrides=never."" Therefore, this macro will not work on nested attachments.", _
            vbOKOnly Or vbExclamation, "Configuration Variable Warning"
        Exit Sub
    End If

'    If ActiveModelReference.Type <> msdModelTypeDrawing And ActiveModelReference.Type <> msdModelTypeSheet Then
'        MsgBox "This macro must be run from a Sheet or Drawing model.", vbOKOnly Or vbExclamation, "Wrong Model Type"
'    Else
        If FormMain.lbFiles.ListCount > 0 Then
            For i = 1 To FormMain.lbFiles.ListCount
                FormMain.lbFiles.RemoveItem (FormMain.lbFiles.ListCount - 1)
            Next
        End If
        If FormMain.ComboDrive.ListCount = 0 Then
            FormMain.ComboDrive.AddItem "A:\"
            FormMain.ComboDrive.AddItem "B:\"
            FormMain.ComboDrive.AddItem "C:\"
            FormMain.ComboDrive.AddItem "D:\"
            FormMain.ComboDrive.AddItem "E:\"
            FormMain.ComboDrive.AddItem "F:\"
            FormMain.ComboDrive.AddItem "G:\"
            FormMain.ComboDrive.AddItem "H:\"
            FormMain.ComboDrive.AddItem "I:\"
            FormMain.ComboDrive.AddItem "J:\"
            FormMain.ComboDrive.AddItem "K:\"
            FormMain.ComboDrive.AddItem "L:\"
            FormMain.ComboDrive.AddItem "M:\"
            FormMain.ComboDrive.AddItem "N:\"
            FormMain.ComboDrive.AddItem "O:\"
            FormMain.ComboDrive.AddItem "P:\"
            FormMain.ComboDrive.AddItem "Q:\"
            FormMain.ComboDrive.AddItem "R:\"
            FormMain.ComboDrive.AddItem "S:\"
            FormMain.ComboDrive.AddItem "T:\"
            FormMain.ComboDrive.AddItem "U:\"
            FormMain.ComboDrive.AddItem "V:\"
            FormMain.ComboDrive.AddItem "W:\"
            FormMain.ComboDrive.AddItem "X:\"
            FormMain.ComboDrive.AddItem "Y:\"
            FormMain.ComboDrive.AddItem "Z:\"
            
            FormMain.ComboDrive.Value = "C:\"
        End If
        
        ' Read the user's settings:
        IniFile = ActiveWorkspace.ConfigurationVariableValue("MS_VBANEWPROJECTDIRECTORY") + "OpenRoads Level Display Batch Processor.ini"
        If Dir(IniFile) <> "" Then
            Open IniFile For Input As #1
            Input #1, Val
            FormMain.cbActiveFile.Value = Val
            Input #1, Val
            FormMain.ChkEscludi.Value = Val
            Input #1, Val
            FormMain.TxtEscludi.Value = Val
            Input #1, Val
            FormMain.ChkIncludi.Value = Val
            Input #1, Val
            FormMain.TxtIncludi.Value = Val
            Input #1, Val
            FormMain.cbToggleRefs.Value = Val
            Input #1, Val
            FormMain.Top = Val
            Input #1, Val
            FormMain.Left = Val
            Close #1
        End If
        
        FormMain.Show (Modal)
'    End If
End Sub
