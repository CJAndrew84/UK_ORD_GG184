Attribute VB_Name = "Module1"
Option Explicit
Dim oMdl As ModelReference
Dim sFileBaseName As String
Dim nModels As Integer
Const CfgVar_sFileBaseName As String = "$(basename(_DGNFILE))"
Public Sub RenameModel()
sFileBaseName = ActiveWorkspace.ExpandConfigurationVariable(CfgVar_sFileBaseName)

On Error Resume Next
    nModels = CountModels(msdModelTypeNormal)
    For Each oMdl In ActiveModelReference.DesignFile.Models
        If oMdl.Type = msdModelTypeSheet Then
            oMdl.Name = "(PS)" & sFileBaseName
        ElseIf oMdl.Type = msdModelTypeNormal Then
            If nModels = 1 Then
                oMdl.Name = "(DM)" & sFileBaseName
                oMdl.Description = "Master Model"
            ElseIf nModels >= 2 Then
                If oMdl = ActiveDesignFile.DefaultModelReference Then
                   oMdl.Name = "(DM)" & sFileBaseName
                Else
                    UserFormRenameDesignModel.Label1 = "Only the Default Design Model can be named " & "(DM)" & sFileBaseName & vbCrLf & "Rename existing model currently named " & """" & oMdl.Name & """" & " below"
                    UserFormRenameDesignModel.TextBox1 = "(DM)" & oMdl.Name
                    UserFormRenameDesignModel.show
                End If
            End If
        End If
    Next
End Sub

Attribute VB_Name = "modUpdateCrossSections"
Option Explicit

Public Sub UpdateCrossSections()
    
    CadInputQueue.SendKeyin "GEOMETRY UNANNOTATE BULK "
    
    CadInputQueue.SendKeyin "REFERENCE VISIBLEEDGES ALLMODELS SYNCHRONIZECACHE "
    
    CadInputQueue.SendKeyin "GEOMETRY ANNOTATE BULK "
    

End Sub
