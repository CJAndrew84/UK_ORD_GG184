Attribute VB_Name = "Module1"
' Macro for multi-user itl template library use - Created by Mark Shamoun (Arcadis NSW)
' -----------------------------------------------------------------------------------------------

Declare Sub Sleep Lib "Kernel32" (ByVal dwMilliseconds As Long)
Declare Function WNetGetUser Lib "mpr.dll" Alias "WNetGetUserA" (ByVal lpName As String, ByVal lpUserName As String, lpnLength As Long) As Long
Sub run()

Const CfgVarName As String = "CIVIL_ROADWAY_TEMPLATE_LIBRARY"

Dim cfgVarValue As String, LocUser As String, GetFileOwner As String
Dim Currvalue As String, Newvalue As String, itlPath As String


' Get current variable for itl location
Currvalue = ActiveWorkspace.ConfigurationVariableValue(CfgVarName)


' Run normally if itl located on local drive (ie. C or D) - disable if using sync software
If FileExists(Currvalue) And Not (Left(Currvalue, 1) = "C") And Not (Left(Currvalue, 1) = "D") Then


' Split full itl path into array
i = 0
arval = Split(Currvalue, "\")
For i = 0 To UBound(arval)
Next i
                
                
' Get current folder for itl location
MyLen1 = Len(Currvalue)
MyLen2 = Len(arval(i - 1))
MyLen3 = MyLen1 - MyLen2
itlPath = Left(Currvalue, MyLen3)


' Create blank.itl file for initial itl open
Dim fso As Object
Set fso = CreateObject("Scripting.FileSystemObject")
Dim oFile As Object
Set oFile = fso.CreateTextFile(itlPath + "\blank.itl")
itltext = "<InRoads productName=" + Chr(34) + Chr(34) + " productVersion=" + Chr(34) + "08.11.09.878" + Chr(34) + " outputGridScaleFactor=" + Chr(34) + "1.00000000" + Chr(34) + " inputGridScaleFactor=" + Chr(34) + "1.00000000" + Chr(34) + " linearUnits=" + Chr(34) + "Metric" + Chr(34) + " angularUnits=" + Chr(34) + "Degrees" + Chr(34) + " commandName=" + Chr(34) + "Saved Template Library" + Chr(34) + "><TemplateLibrary lastRevisedDate=" + Chr(34) + "25/03/2017 7:56:17 PM" + Chr(34) + " lastRevisedBy=" + Chr(34) + "msaz3224" + Chr(34) + " fileName=" + Chr(34) + "C:\ProgramData\Bentley\MX V8i (SELECTseries 4)\WorkSpace\Projects\Arcadis-NSW\OpenRoads\Templates\blank.itl" + Chr(34) + "><Category/></TemplateLibrary></InRoads>"
oFile.WriteLine itltext
oFile.Close
Set fso = Nothing
Set oFile = Nothing


' Get current windows username
    ' Buffer size for the return string.
Const lpnLength As Integer = 255
    ' Get return buffer space.
Dim status As Integer
    ' For getting user information.
Dim lpName, lpUserName As String
    ' Assign the buffer size constant to lpUserName.
lpUserName = Space$(lpnLength + 1)
    ' Get the log-on name of the person using product.
status = WNetGetUser(lpName, lpUserName, lpnLength)
lpUserName = Left$(lpUserName, InStr(lpUserName, Chr(0)) - 1)


' Check if loc file exists and if created by current user delete loc file.
If FileExists(Currvalue + ".loc") Then
    Open Currvalue + ".loc" For Input As #1
    Do Until EOF(1)
        Line Input #1, LocUser
    Loop
    Close #1
    
    ' Check if current user created loc file
    If LocUser = Chr(34) + lpUserName + Chr(34) Then
    ' if so, delete temp loc file
    Kill Currvalue + ".loc"
    End If
End If


If LocUser = "" Then
    LocUser = "unknown"
End If


' Check if loc file exists and display error if itl is in use
If FileExists(Currvalue + ".loc") Then

    '' Get Loc file owner
    'Dim obj As Object
    'Dim fso As Object
    'Set fso = CreateObject("Scripting.FileSystemObject")
    'Set obj = CreateObject("Shell.Application")
    'With obj.Namespace(fso.GetParentFolderName(Currvalue + ".loc"))
    '   'return extended file property 9 of file indexed by name
    '   getfileAuthor = .GetDetailsOf(.Items.Item(fso.GetFileName(Currvalue + ".loc")), 10)
    'End With

    CadInputQueue.SendCommand "beep"
    ShowMessage "ITL file: " + Chr(34) + Currvalue + Chr(34) + " in use by User: " + LocUser
    ShowMessage "ERROR - Template Library is currently being edited by " + LocUser + ". Try again later.", , msdMessageCenterPriorityError
    MsgBox "ERROR - Template Library is currently being edited by " + LocUser + ". Try again later. See Message Center for more info."
    Exit Sub
End If


' Create loc file to indicate itl is in use & write username
Open Currvalue + ".loc" For Output As #2
Write #2, lpUserName
Close #2


' Replace variable with temp blank itl
Newvalue = Left(Currvalue, MyLen3) + "blank.itl"
CadInputQueue.SendCommand "expand set " + CfgVarName + " = " + Newvalue


' Open blank itl template library and close immediately
SendKeys "%{F4}"
CadInputQueue.SendCommand "corridor templatelibrary open"


' Reset itl location and open template library
CadInputQueue.SendCommand "expand set " + CfgVarName + " = " + Currvalue

' Backup current itl
FileCopy Currvalue, Currvalue + ".bak"

' Open itl template library
CadInputQueue.SendCommand "corridor templatelibrary open"


' Delete temp loc file
Kill Currvalue + ".loc"

' Exit Macro
Exit Sub

Else

' Open itl template library normally

If Not (FileExists(Currvalue)) Then
    CadInputQueue.SendCommand "beep"
    ShowMessage "ERROR - " + Currvalue + " not found", , msdMessageCenterPriorityError
End If

CadInputQueue.SendCommand "corridor templatelibrary open"


End If

CadInputQueue.SendCommand "powerselector single"

End Sub

Function FileExists(ByVal strFile As String, Optional bFindFolders As Boolean) As Boolean
    'Purpose:   Return True if the file exists, even if it is hidden.
    'Arguments: strFile: File name to look for. Current directory searched if no path included.
    '           bFindFolders. If strFile is a folder, FileExists() returns False unless this argument is True.
    'Note:      Does not look inside subdirectories for the file.
    'Author:    Allen Browne. http://allenbrowne.com June, 2006.
    Dim lngAttributes As Long

    'Include read-only files, hidden files, system files.
    lngAttributes = (vbReadOnly Or vbHidden Or vbSystem)

    If bFindFolders Then
        lngAttributes = (lngAttributes Or vbDirectory) 'Include folders as well.
    Else
        'Strip any trailing slash, so Dir does not look inside the folder.
        Do While Right$(strFile, 1) = "\"
            strFile = Left$(strFile, Len(strFile) - 1)
        Loop
    End If

    'If Dir() returns something, the file exists.
    On Error Resume Next
    FileExists = (Len(Dir(strFile, lngAttributes)) > 0)
End Function
