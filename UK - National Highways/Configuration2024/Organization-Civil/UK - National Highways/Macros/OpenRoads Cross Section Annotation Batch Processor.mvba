Attribute VB_Name = "FormMain"
Attribute VB_Base = "0{63AF4A10-DFA8-48F8-A4AE-C12D1B792506}{F2D9CCE9-76FF-4DC0-A0E0-C110DE3F4AA9}"
Attribute VB_GlobalNameSpace = False
Attribute VB_Creatable = False
Attribute VB_PredeclaredId = True
Attribute VB_Exposed = False
Attribute VB_TemplateDerived = False
Attribute VB_Customizable = False
Option Explicit
        
Private Sub CmdOK_Click()
    
    Dim Response
    Dim i As Integer
    
    Me.Hide
    
    ' Make sure user has selected files to be processed:
    If Me.lbFiles.ListCount = 0 Then
        Response = MsgBox("Please select files to be processed", vbOKCancel Or vbExclamation, "Select Files")
        If Response <> vbCancel Then
            Me.Show
        Else
            Exit Sub
        End If
    End If
    
    ' Open each file in the listbox:
    For i = 0 To lbFiles.ListCount - 1
        If lbFiles.Selected(i) = True Then
            ProcessFile lbFiles.List(i)
        End If
    Next i
    
    CommandState.StartDefaultCommand
End Sub

Private Sub ProcessFile(dgnFileName As String)

    Dim oModel As ModelReference

    OpenDesignFile dgnFileName
    
    For Each oModel In ActiveDesignFile.Models
        If oModel.Type = msdModelTypeDrawing Then
            Call ProcessModel(oModel)
            
            ' Only process one drawing model per file:
            Exit For
        End If
    Next
End Sub

Private Sub ProcessModel(oModel As ModelReference)

    Dim ciMessage As CadInputMessage
    
    oModel.Activate
    
    ' Delete existing annotations?
    If Me.cbDeleteExistAnnotations.Value = True Then
        CadInputQueue.SendKeyin "GEOMETRY UNANNOTATE BULK "
        'CadInputQueue.SendKeyin "CIVILCMD SETVALUE AllDrawingModels=<AllDrawingModels>True,False</AllDrawingModels> "
        Set ciMessage = CadInputQueue.GetInput
        Select Case ciMessage.InputType
            Case msdCadInputTypeDataPoint
                CadInputQueue.SendDataPoint ciMessage.Point
        End Select
    End If
    
    ' Generate new annotations:
    CadInputQueue.SendKeyin "GEOMETRY ANNOTATE BULK "
    
    ' At the end of the process, the Element Selection tool will be activated by the program. Test for this condition:
    Do While CommandState.CommandName <> "Element Selection"
        Set ciMessage = CadInputQueue.GetInput
        Select Case ciMessage.InputType
            Case msdCadInputTypeDataPoint
                CadInputQueue.SendDataPoint ciMessage.Point
        End Select
    Loop
End Sub

Private Sub CmdCancel_Click()

    Me.Hide
End Sub

Private Sub cmdBrowseFile_Click()
    
    Dim dgnFile  As String
    Dim i As Integer
    Dim slashpos As Integer
    Dim FilePath As String
    Dim filename As String
    Dim r As Integer
    
    dgnFile = ShowOpen("Open Design File", "OpenedUsingCommonDialog", "MicroStation Files (*.dgn)", "*.dgn", "D:\temp")
    If dgnFile <> "" Then
        i = 1
        Do While i < Len(dgnFile)
            If Mid$(dgnFile, i, 1) = "\" Then
                slashpos = i
            End If
            i = i + 1
        Loop
        
        Me.lbFiles.AddItem dgnFile
        For r = 0 To lbFiles.ListCount - 1
            If r = lbFiles.ListCount - 1 Then
                lbFiles.Selected(r) = True
            End If
        Next r
    End If
End Sub

Private Sub cmdBrowseFolder_Click()

    Dim Ret As String
    Dim FileFolder As String
    Dim filename As String
    Dim r As Integer

    '~~> Specify your start folder here
    Ret = BrowseForFolder(Me.ComboDrive.Value)
    If Ret <> "" Then
        'Debug.Print Ret
        FileFolder = Ret + "\"
        
        ' Returns filename with specified extension. If more than one *.ini
        ' file exists, the first file found is returned.
        filename = Dir(FileFolder + "*.dgn")
        Do While filename <> ""
            Me.lbFiles.AddItem FileFolder + filename
            For r = 0 To lbFiles.ListCount - 1
                If r = lbFiles.ListCount - 1 Then
                    lbFiles.Selected(r) = True
                End If
            Next r

            ' Call Dir again without arguments to return the next *.INI file in the
            ' same directory.
            filename = Dir
        Loop
    End If
End Sub

Function BrowseForFolder(Optional OpenAt As Variant) As Variant
     'Function purpose:  To Browser for a user selected folder.
     'If the "OpenAt" path is provided, open the browser at that directory
     'NOTE:  If invalid, it will open at the Desktop level

    Dim ShellApp As Object

     'Create a file browser window at the default folder
    Set ShellApp = CreateObject("Shell.Application"). _
    BrowseForFolder(0, "Please choose a folder", 0, OpenAt)

     'Set the folder to that selected.  (On error in case cancelled)
    On Error Resume Next
    BrowseForFolder = ShellApp.self.Path
    'Debug.Print ShellApp.self.Path
    On Error GoTo 0

     'Destroy the Shell Application
    Set ShellApp = Nothing

     'Check for invalid or non-entries and send to the Invalid error
     'handler if found
     'Valid selections can begin L: (where L is a letter) or
     '\\ (as in \\servername\sharename.  All others are invalid
    Select Case Mid(BrowseForFolder, 2, 1)
    Case Is = ":"
        If Left(BrowseForFolder, 1) = ":" Then GoTo Invalid
    Case Is = "\"
        If Not Left(BrowseForFolder, 1) = "\" Then GoTo Invalid
    Case Else
        GoTo Invalid
    End Select

    Exit Function

Invalid:
     'If it was determined that the selection was invalid, set to False
    BrowseForFolder = False
End Function

Private Sub UserForm_QueryClose(Cancel As Integer, CloseMode As Integer)

    Dim IniFile As String

    ' Save the user's settings:
    IniFile = "C:\ProgramData\Bentley\OpenRoads Cross Section Annotation Batch Processor.ini"
    Open IniFile For Output As #1
    Write #1, Me.cbDeleteExistAnnotations.Value
    Write #1, Me.Top
    Write #1, Me.Left
    Close #1

End Sub

Attribute VB_Name = "clsDisplayInfo"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False

Public LevelName As String
Public IsDisplayed As Boolean

Attribute VB_Name = "modCommonDialogs"
Option Explicit
' --------------------------------------------------------------------
Private Declare PtrSafe Function GetOpenFileName Lib "comdlg32.dll" Alias "GetOpenFileNameA" ( _
    ByRef pOpenfilename As OPENFILENAME) As Long
Private Declare PtrSafe Function GetSaveFileName Lib "comdlg32.dll" Alias "GetSaveFileNameA" ( _
    ByRef pOpenfilename As OPENFILENAME) As Long

' ---------------------------------------------------------------------
'   Win32 API structure definition as user-defined type
' ---------------------------------------------------------------------
Private Type OPENFILENAME
  lStructSize As Long
  hwndOwner As LongPtr
  hInstance As LongPtr
  lpstrFilter As String
  lpstrCustomFilter As String
  nMaxCustFilter As Long
  nFilterIndex As Long
  lpstrFile As String
  nMaxFile As Long
  lpstrFileTitle As String
  nMaxFileTitle As Long
  lpstrInitialDir As String
  lpstrTitle As String
  flags As Long
  nFileOffset As Integer
  nFileExtension As Integer
  lpstrDefExt As String
  lCustData As Long
  lpfnHook As LongPtr
  lpTemplateName As String
End Type
' ---------------------------------------------------------------------
'   Win32 API constants
' ---------------------------------------------------------------------
Private Const BIF_NEWDIALOGSTYLE         As Long = &H40
Private Const BIF_RETURNONLYFSDIRS       As Long = 1
Private Const MAX_PATH                   As Long = 260
Private Const OFN_OVERWRITEPROMPT        As Long = &H2
Private Const OFN_FILEMUSTEXIST          As Long = &H1000
Private Const OFN_PATHMUSTEXIST          As Long = &H800
Private Const OFN_ALLOWMULTISELECT As Long = &H200
' ---------------------------------------------------------------------
'   ShowSave    Save As... common dialog
'   Arguments:  [in, String] dialog title,
'               [in, String] filter description, [optional]
'               [in, String] filter spec, [optional]
'               [in, String] default directory [optional]
'   Example call:
'   dgnFile = ShowSave ("Save Design File As...", "SavedUsingCommonDialog", _
'   "MicroStation Files (*.dgn)", "*.dgn", "V:\shared")
'   Returns:    full path of file to be saved
' ---------------------------------------------------------------------
Public Function ShowSave( _
    ByVal strDialogTitle As String, _
    ByVal strProposed As String, _
    Optional ByVal strFilterDescr As String = "All files (*.*)", _
    Optional ByVal strFilterSpec As String = "*.*", _
    Optional ByVal strDefaultDir As String = vbNullString) As String
    On Error Resume Next
    Dim strFilter                           As String, _
        strFileSelected                     As String, _
        proposed                            As String
    Dim OFName                              As OPENFILENAME
    strFilter = strFilterDescr + Chr$(0) + strFilterSpec + Chr$(0)

    proposed = strProposed & Chr$(0) & Space$(254 - Len(strProposed)) 'Create a buffer
    Const Period                            As String = "."
    With OFName
        .lStructSize = LenB(OFName) ' Set the structure size.  Note use of LenB() not Len()
        .hwndOwner = 0& ' Set the owner window
        .hInstance = 0& ' Set the application's instance
        .lpstrFilter = strFilter 'Set the filter
        .lpstrFile = proposed
        .lpstrDefExt = Mid$(strFilterSpec, 1 + InStr(strFilterSpec, Period))
        .nMaxFile = 255 ' Set the maximum number of chars
        .lpstrFileTitle = Space$(254) ' Create a buffer
        .nMaxFileTitle = 255 'Set the maximum number of chars
        If (vbNullString <> strDefaultDir) Then _
            .lpstrInitialDir = strDefaultDir 'Set the initial directory
        .lpstrTitle = strDialogTitle 'Set the dialog title
        .flags = OFN_OVERWRITEPROMPT 'no extra flags
    End With
    If GetSaveFileName(OFName) Then 'Show the 'Save File' dialog
        strFileSelected = Trim$(OFName.lpstrFile)
        If (InStr(strFileSelected, Chr(0)) > 0) Then
            strFileSelected = Left(strFileSelected, InStr(strFileSelected, Chr(0)) - 1)
        End If
        ShowSave = Trim(strFileSelected)
    Else
        ShowSave = ""
    End If
End Function
' ---------------------------------------------------------------------
'   ShowOpen    Open common dialog
'   Arguments:  [in, String] dialog title,
'               [in, String] proposed name, [optional]
'               [in, String] filter description, [optional]
'               [in, String] filter spec, [optional]
'               [in, String] default directory [optional]
'   Example call:
'   dgnFile = ShowOpen ("Open Design File", "MicroStation Files (*.dgn)", "*.dgn", "V:\shared")
'   Returns:    full path of file to be opened
' ---------------------------------------------------------------------
Public Function ShowOpen(ByVal title As String, _
        ByVal proposedName As String, _
        ByVal filterDescription As String, _
        ByVal filter As String, _
        ByVal initialDirectory As String) As String
    ShowOpen = vbNullString
    
    On Error Resume Next
    Dim strFilter                           As String, _
        strFileSelected                     As String, _
        proposed                            As String
    Dim OFName                              As OPENFILENAME
    strFilter = filterDescription + Chr$(0) + filter + Chr$(0)

    proposed = proposedName & Chr$(0) & Space$(254 - Len(proposed)) 'Create a buffer
    Const Period                            As String = "."
    With OFName
        .lStructSize = LenB(OFName) ' Set the structure size.  Note use of LenB() not Len()
        .hwndOwner = 0& ' Set the owner window
        .hInstance = 0& ' Set the application's instance
        .lpstrFilter = strFilter 'Set the filter
        .lpstrFile = proposed
        .lpstrDefExt = Mid$(filter, 1 + InStr(filter, Period))
        .nMaxFile = 255 ' Set the maximum number of chars
        .lpstrFileTitle = Space$(254) ' Create a buffer
        .nMaxFileTitle = 255 'Set the maximum number of chars
        If (vbNullString <> initialDirectory) Then _
            .lpstrInitialDir = initialDirectory 'Set the initial directory
        .lpstrTitle = title 'Set the dialog title
        .flags = OFN_FILEMUSTEXIST
    End With
    If GetOpenFileName(OFName) Then 'Show the 'Open File' dialog
        strFileSelected = Trim$(OFName.lpstrFile)
        If (InStr(strFileSelected, Chr(0)) > 0) Then
            strFileSelected = Left(strFileSelected, InStr(strFileSelected, Chr(0)) - 1)
        End If
        ShowOpen = Trim(strFileSelected)
    Else
        ShowOpen = vbNullString
    End If
End Function
' --------------------------------------------------------------------

Attribute VB_Name = "modCrossSectionAnno"

Sub Main()
    
    ' Developed by Bentley Systems.
    ' Intended for use on models created by OpenRoads Designer.
    
    Dim i As Integer
    Dim Value As Integer
    Dim ValStr As String
    Dim Val
    
    On Error Resume Next
    
    If FormMain.lbFiles.ListCount > 0 Then
        For i = 1 To FormMain.lbFiles.ListCount
            FormMain.lbFiles.RemoveItem (FormMain.lbFiles.ListCount - 1)
        Next
    End If
    If FormMain.ComboDrive.ListCount = 0 Then
        FormMain.ComboDrive.AddItem "A:\"
        FormMain.ComboDrive.AddItem "B:\"
        FormMain.ComboDrive.AddItem "C:\"
        FormMain.ComboDrive.AddItem "D:\"
        FormMain.ComboDrive.AddItem "E:\"
        FormMain.ComboDrive.AddItem "F:\"
        FormMain.ComboDrive.AddItem "G:\"
        FormMain.ComboDrive.AddItem "H:\"
        FormMain.ComboDrive.AddItem "I:\"
        FormMain.ComboDrive.AddItem "J:\"
        FormMain.ComboDrive.AddItem "K:\"
        FormMain.ComboDrive.AddItem "L:\"
        FormMain.ComboDrive.AddItem "M:\"
        FormMain.ComboDrive.AddItem "N:\"
        FormMain.ComboDrive.AddItem "O:\"
        FormMain.ComboDrive.AddItem "P:\"
        FormMain.ComboDrive.AddItem "Q:\"
        FormMain.ComboDrive.AddItem "R:\"
        FormMain.ComboDrive.AddItem "S:\"
        FormMain.ComboDrive.AddItem "T:\"
        FormMain.ComboDrive.AddItem "U:\"
        FormMain.ComboDrive.AddItem "V:\"
        FormMain.ComboDrive.AddItem "W:\"
        FormMain.ComboDrive.AddItem "X:\"
        FormMain.ComboDrive.AddItem "Y:\"
        FormMain.ComboDrive.AddItem "Z:\"
        
        FormMain.ComboDrive.Value = "C:\"
    End If
    
    ' Read the user's settings:
    IniFile = "C:\ProgramData\Bentley\OpenRoads Cross Section Annotation Batch Processor.ini"
    If Dir(IniFile) <> "" Then
        Open IniFile For Input As #1
        Input #1, Val
        FormMain.cbDeleteExistAnnotations.Value = Val
        Input #1, Val
        FormMain.Top = Val
        Input #1, Val
        FormMain.Left = Val
        Close #1
    End If
    
    FormMain.Show (Modal)
End Sub
